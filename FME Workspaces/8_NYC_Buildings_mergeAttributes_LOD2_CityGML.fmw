FME workspace 8_NYC_Buildings_mergeAttributes_LOD2_CityGML.fmw

Parameters:
- SourceDataset_CITYGML = Y:\TUM Geoinformatik\NYC Buildings\Datengrundlage\Buildings Burger\Buildings_wo_Geometry_Burger\Buildings_wo_Geometry_Burger.gml   # Source CityGML File(s)
- DestDataset_CITYGML = F:\Straßenraummodell Version 2.0\LoD2 Buildings mit Attributen\Buildings mit Attributen - 20 Files\Buildings_NYC_CityGML_20   # Destination CityGML Document
- SourceDataset_CITYGML_3 = Y:\TUM Geoinformatik\NYC Buildings\Datengrundlage\DA_WISE_GMLs\DA20_3D_Buildings_Merged.gml   # Source CityGML File(s)

Readers:
- CITYGML_1: CITYGML from $(SourceDataset_CITYGML)
- CITYGML_2: CITYGML from $(SourceDataset_CITYGML_3)

Writers:
- CITYGML_3: CITYGML to $(DestDataset_CITYGML)

Bookmark: Create City Model
Creator
    NUM = 1
    GEOMTYPE = Geometry Object
    CREATED -> AttributeCreator_15
AttributeCreator_15
    ATTR_TABLE:
      SET_TO gml_name = Buildings_NYC_CityGML_1
      SET_TO gml_id = Buildings_NYC_CityGML_1
    -> CityModel (writer CITYGML_3)
CityModel (writer CITYGML_3)
    attributes: gml_name xml_buffer, _creation_instance xml_char(200)

Bookmark: Building Attributes TUM LOD1 CityGML
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_usage{} xml_buffer, citygml_year_of_construction xml_buffer, citygml_year_of_demolition xml_buffer, citygml_roof_type xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer,
      citygml_level_of_detail{} xml_buffer, citygml_interior_room{}.xlink_href xml_buffer, citygml_consists_of_building_part{}.xlink_href xml_buffer, citygml_address{}.xlink_href xml_buffer, Adress_bin xml_buffer, GE_LoD1_zOffset xml_buffer, OBJECTID xml_buffer, PLUTO_area_source xml_buffer, PLUTO_building_area xml_buffer, PLUTO_building_class xml_buffer, PLUTO_building_depth xml_buffer, PLUTO_building_frontage xml_buffer, PLUTO_built_floor_area_ratio xml_buffer, PLUTO_commercial_area xml_buffer, PLUTO_condominium_number xml_buffer, PLUTO_factory_area xml_buffer, PLUTO_garage_area xml_buffer, PLUTO_land_use_category xml_buffer, PLUTO_lot_address xml_buffer, PLUTO_number_of_floors xml_buffer, PLUTO_office_area xml_buffer, PLUTO_other_area xml_buffer, PLUTO_proximity_code xml_buffer, PLUTO_residential_area xml_buffer, PLUTO_retail_area xml_buffer, PLUTO_storage_area xml_buffer, PLUTO_units_residential xml_buffer, PLUTO_year_altered_1 xml_buffer, PLUTO_year_altered_2 xml_buffer, PLUTO_year_built xml_buffer,
      PLUTO_year_built_code xml_buffer, borough_block_lot_number xml_buffer, building_base_area xml_buffer, building_identification_nuber xml_buffer, building_under_construction xml_buffer, building_volume xml_buffer, doitt_id xml_buffer, geom_source xml_buffer, ground_elevation xml_buffer, last_modify_date xml_buffer, last_status_1 xml_buffer, last_status_type xml_buffer, source_id xml_buffer, status xml_buffer
    -> AttributeRemover_2

Bookmark: Pre processing
AttributeRemover_2
    REMOVE_ATTRS = citygml_level_of_detail{0},citygml_feature_role,citygml_target_uri,gml_parent_id
    -> AttributeRenamer
AttributeRenamer
    ATTR_TABLE = RENAME_SET_DEFAULT gml_id > externalReference{1}.externalObject.name
    -> AttributeCreator
AttributeCreator
    ATTR_TABLE:
      SET_TO externalReference{1}.informationSystem = https://www.gis.bgu.tum.de/projekte/new-york-city-3d/
      SET_TO building_identification_number = @Value(building_identification_nuber)
    -> AttributeKeeper
AttributeKeeper
    KEEP_LIST = citygml_function{} citygml_usage{}
    KEEP_ATTRS = PLUTO_storage_area,citygml_measured_height,last_status_1,externalReference{0}.informationSystem,PLUTO_building_class,citygml_roof_type,PLUTO_office_area,building_under_construction,externalReference{2}.externalObject.name,building_volume,GE_LoD1_zOffset,PLUTO_retail_area,citygml_storey_heights_above_ground,building_identification_number,OBJECTID,PLUTO_land_use_category,citygml_year_of_demolition,PLUTO_built_floor_area_ratio,PLUTO_number_of_floors,citygml_address{0}.xlink_href,source_id,borough_block_lot_number,citygml_usage{0},ground_elevation,status,Adress_bin,PLUTO_other_area,citygml_year_of_construction,gml_name,externalReference{0}.externalObject.uri,PLUTO_year_built_code,PLUTO_garage_area,PLUTO_units_residential,externalReference{1}.informationSystem,externalReference{2}.informationSystem,citygml_class,last_modify_date,PLUTO_building_area,PLUTO_lot_address,building_base_area,PLUTO_commercial_area,citygml_measured_height_units,citygml_storey_heights_below_ground_units,PLUTO_year_built,PLUTO_area_source,PLUTO_year_altered_1,externalReference{1}.externalObject.name,externalReference{0}.externalObject.name,last_status_type,citygml_storey_heights_below_ground,citygml_function{0},citygml_storey_heights_above_ground_units,PLUTO_building_frontage,doitt_id,geom_source,citygml_storeys_above_ground,gml_description,PLUTO_residential_area,citygml_storeys_below_ground,PLUTO_proximity_code,PLUTO_building_depth,PLUTO_year_altered_2,PLUTO_condominium_number,PLUTO_factory_area
    -> GeometryRemover
GeometryRemover
    -> FeatureMerger_7 [SUPPLIER]
CsmapReprojector_2
    INTERPOLATION_TYPE_NAME = Nearest Neighbor
    VERTICAL_HANDLING = NAD27 heights in NGVD29; NAD83 heights in NAVD88
    DEST = EPSG:32118
    RASTER_CELL_SIZE = Preserve Cells
    REPROJECTED -> AttributeExposer_2
AttributeExposer_2
    ATTR_LIST = fme_feature_type
    -> AttributeCreator_8
AttributeCreator_8
    ATTR_TABLE:
      SET_TO externalReference{0}.externalObject.name = @Value(gml_id)
      SET_TO externalReference{0}.informationSystem = http://www1.nyc.gov/site/doitt/initiatives/3d-building.page
    -> AttributeRenamer_5
AttributeRenamer_5
    ATTR_TABLE = RENAME_SET_DEFAULT gml_name > building_name_NYC
    -> AttributeRemover_3
AttributeRemover_3
    REMOVE_ATTRS = SOURCE_ID,DOITT_ID
    -> FeatureMerger_7 [REQUESTOR]
CsmapReprojector
    INTERPOLATION_TYPE_NAME = Nearest Neighbor
    VERTICAL_HANDLING = NAD27 heights in NGVD29; NAD83 heights in NAVD88
    DEST = EPSG:32118
    RASTER_CELL_SIZE = Preserve Cells
    REPROJECTED -> AttributeExposer_3
AttributeExposer_3
    ATTR_LIST = fme_feature_type
    -> AttributeCreator_3
AttributeCreator_3
    ATTR_TABLE:
      SET_TO externalReference{0}.externalObject.name = @Value(gml_id)
      SET_TO externalReference{0}.informationSystem = http://www1.nyc.gov/site/doitt/initiatives/3d-building.page
    -> AttributeRemover_7
AttributeRemover_7
    REMOVE_ATTRS = SOURCE_ID,DOITT_ID
    -> AreaCalculator
CsmapReprojector_4
    INTERPOLATION_TYPE_NAME = Nearest Neighbor
    VERTICAL_HANDLING = NAD27 heights in NGVD29; NAD83 heights in NAVD88
    DEST = EPSG:32118
    RASTER_CELL_SIZE = Preserve Cells
    REPROJECTED -> AttributeExposer_4
AttributeExposer_4
    ATTR_LIST = fme_feature_type
    -> AttributeCreator_5
AttributeCreator_5
    ATTR_TABLE:
      SET_TO externalReference{0}.externalObject.name = @Value(gml_id)
      SET_TO externalReference{0}.informationSystem = http://www1.nyc.gov/site/doitt/initiatives/3d-building.page
    -> AttributeRemover_8
AttributeRemover_8
    REMOVE_ATTRS = SOURCE_ID,DOITT_ID
    -> AreaCalculator_2
CsmapReprojector_5
    INTERPOLATION_TYPE_NAME = Nearest Neighbor
    VERTICAL_HANDLING = NAD27 heights in NGVD29; NAD83 heights in NAVD88
    DEST = EPSG:32118
    RASTER_CELL_SIZE = Preserve Cells
    REPROJECTED -> AttributeExposer_5
AttributeExposer_5
    ATTR_LIST = fme_feature_type
    -> AttributeCreator_7
AttributeCreator_7
    ATTR_TABLE:
      SET_TO externalReference{0}.externalObject.name = @Value(gml_id)
      SET_TO externalReference{0}.informationSystem = http://www1.nyc.gov/site/doitt/initiatives/3d-building.page
    -> AttributeRemover_10
AttributeRemover_10
    REMOVE_ATTRS = SOURCE_ID,DOITT_ID
    -> AreaCalculator_3

Bookmark: Buildings NYC LoD 2 CityGML
Building (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_usage{} xml_buffer, citygml_year_of_construction xml_buffer, citygml_year_of_demolition xml_buffer, citygml_roof_type xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer,
      citygml_level_of_detail{} xml_buffer, citygml_interior_room{}.xlink_href xml_buffer, citygml_consists_of_building_part{}.xlink_href xml_buffer, citygml_address{}.xlink_href xml_buffer, BIN xml_buffer, DOITT_ID xml_buffer, SOURCE_ID xml_buffer
    -> CsmapReprojector_2
RoofSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer, BIN xml_buffer, DOITT_ID xml_buffer, SOURCE_ID xml_buffer
    -> CsmapReprojector
WallSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer, BIN xml_buffer, DOITT_ID xml_buffer, SOURCE_ID xml_buffer
    -> CsmapReprojector_4
GroundSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer, BIN xml_buffer, DOITT_ID xml_buffer, SOURCE_ID xml_buffer
    -> CsmapReprojector_5

Bookmark: Merge Attributes
FeatureMerger_7
    MERGE_TYPE = Attributes Only
    JOIN_KEYS = @Value(BIN) @Value(building_identification_number) AUTO
    REJECT_NULL_MISSING_KEYS = Yes
    ATTR_CONFLICT_RES = Use Requestor
    SUPPLIERS_FIRST = No
    IGNORE_NULLS = No
    ATTR_ACCUM_MODE = Merge Supplier
    PROCESS_DUPS = No
    MERGED -> AttributeKeeper_2
    NOT_MERGED -> AttributeKeeper_2
AttributeKeeper_2
    KEEP_LIST = citygml_function{} citygml_level_of_detail{} citygml_usage{} externalReference{}
    KEEP_ATTRS = status,citygml_roof_type,PLUTO_storage_area,source_id,PLUTO_lot_address,PLUTO_building_depth,PLUTO_year_built,building_volume,last_status_type,PLUTO_residential_area,citygml_storeys_below_ground,PLUTO_retail_area,citygml_storey_heights_below_ground_units,PLUTO_units_residential,PLUTO_area_source,citygml_appearance{0}.xlink_href,externalReference{0}.externalObject.uri,externalReference{0}.informationSystem,PLUTO_garage_area,PLUTO_office_area,last_status_1,PLUTO_commercial_area,PLUTO_factory_area,citygml_feature_role,citygml_target_uri,PLUTO_number_of_floors,gml_id,PLUTO_other_area,PLUTO_year_built_code,OBJECTID,borough_block_lot_number,doitt_id,PLUTO_built_floor_area_ratio,citygml_class,citygml_storeys_above_ground,citygml_storey_heights_below_ground,GE_LoD1_zOffset,citygml_function{0},building_identification_number,Adress_bin,gml_parent_id,building_base_area,citygml_measured_height,externalReference{0}.externalObject.name,PLUTO_year_altered_1,last_modify_date,citygml_bounded_by{0}.xlink_href,PLUTO_year_altered_2,PLUTO_building_frontage,citygml_storey_heights_above_ground,PLUTO_building_area,PLUTO_proximity_code,citygml_measured_height_units,citygml_year_of_construction,externalReference{1}.informationSystem,building_name_NYC,citygml_storey_heights_above_ground_units,building_height_meter,citygml_year_of_demolition,citygml_address{0}.xlink_href,externalReference{1}.externalObject.name,building_under_construction,gml_name,geom_source,gml_description,citygml_level_of_detail{0},PLUTO_building_class,PLUTO_land_use_category,PLUTO_condominium_number,ground_elevation,citygml_usage{0}
    -> AttributeFilter
AttributeFilter
    ATTR_NAME = externalReference{0}.externalObject.name
    ATTR_VALUES = <EMPTY>,<MISSING>,<NULL>,<UNFILTERED>
    <MISSING> -> AttributeCreator_2
    <UNFILTERED> -> AttributeFilter_2
AttributeCreator_2
    ATTR_TABLE = SET_TO externalReference{0}.externalObject.name = unknown
    -> AttributeFilter_2
AttributeFilter_2
    ATTR_NAME = externalReference{1}.externalObject.name
    ATTR_VALUES = <EMPTY>,<MISSING>,<NULL>,<UNFILTERED>
    <MISSING> -> AttributeCreator_6
    <UNFILTERED> -> AttributeCopier_2
    <UNFILTERED> -> FeatureMerger [SUPPLIER]
AttributeCreator_6
    ATTR_TABLE = SET_TO externalReference{1}.externalObject.name = unknown
    -> AttributeCopier_2
    -> FeatureMerger [SUPPLIER]
AreaCalculator
    MULT = 1
    AREA_TYPE = Plane Area
    AREA_ATTR = surface_area_sqm
    -> AttributeRounder
AttributeRounder
    PLACES = 3
    ROUND_TYPE = Nearest
    SRC_ATTRS = surface_area_sqm
    -> AttributeRenamer_2
AttributeRenamer_2
    ATTR_TABLE:
      RENAME_SET_DEFAULT BIN > building_identification_number
      RENAME_SET_DEFAULT _slope > roof_slope_degree
    -> AttributeFilter_3
AttributeFilter_3
    ATTR_NAME = externalReference{0}.externalObject.name
    ATTR_VALUES = <EMPTY>,<MISSING>,<NULL>,<UNFILTERED>
    <MISSING> -> AttributeCreator_9
    <UNFILTERED> -> AttributeCopier_4
    <UNFILTERED> -> FeatureMerger [SUPPLIER]
AttributeCreator_9
    ATTR_TABLE = SET_TO externalReference{0}.externalObject.name = unknown
    -> AttributeCopier_4
    -> FeatureMerger [SUPPLIER]
AreaCalculator_2
    MULT = 1
    AREA_TYPE = Plane Area
    AREA_ATTR = surface_area_sqm
    -> AttributeRounder_2
AttributeRounder_2
    PLACES = 3
    ROUND_TYPE = Nearest
    SRC_ATTRS = surface_area_sqm
    -> AttributeRenamer_3
AttributeRenamer_3
    ATTR_TABLE = RENAME_SET_DEFAULT BIN > building_identification_number
    -> AttributeFilter_5
AttributeFilter_5
    ATTR_NAME = externalReference{0}.externalObject.name
    ATTR_VALUES = <EMPTY>,<MISSING>,<NULL>,<UNFILTERED>
    <MISSING> -> AttributeCreator_11
    <UNFILTERED> -> AttributeCopier_3
    <UNFILTERED> -> FeatureMerger [SUPPLIER]
AttributeCreator_11
    ATTR_TABLE = SET_TO externalReference{0}.externalObject.name = unknown
    -> AttributeCopier_3
    -> FeatureMerger [SUPPLIER]
AreaCalculator_3
    MULT = 1
    AREA_TYPE = Plane Area
    AREA_ATTR = surface_area_sqm
    -> AttributeRounder_3
AttributeRounder_3
    PLACES = 3
    ROUND_TYPE = Nearest
    SRC_ATTRS = surface_area_sqm
    -> AttributeRenamer_4
AttributeRenamer_4
    ATTR_TABLE = RENAME_SET_DEFAULT BIN > building_identification_number
    -> AttributeFilter_7
AttributeFilter_7
    ATTR_NAME = externalReference{0}.externalObject.name
    ATTR_VALUES = <EMPTY>,<MISSING>,<NULL>,<UNFILTERED>
    <MISSING> -> AttributeCreator_13
    <UNFILTERED> -> AttributeCopier
    <UNFILTERED> -> FeatureMerger [SUPPLIER]
AttributeCreator_13
    ATTR_TABLE = SET_TO externalReference{0}.externalObject.name = unknown
    -> AttributeCopier
    -> FeatureMerger [SUPPLIER]

Bookmark: Create fanout attribute modulo count for each Building(part)
AttributeCopier_2
    ATTR_TABLE = COPY gml_id > _sort
    -> AttributeExposer
AttributeCopier_4
    ATTR_TABLE = COPY gml_parent_id > _sort
    -> AttributeExposer
AttributeCopier_3
    ATTR_TABLE = COPY gml_parent_id > _sort
    -> AttributeExposer
AttributeCopier
    ATTR_TABLE = COPY gml_parent_id > _sort
    -> AttributeExposer
AttributeExposer
    ATTR_LIST = fme_feature_type
    -> AttributeKeeper_3
AttributeKeeper_3
    KEEP_ATTRS = _sort,fme_feature_type,gml_id
    -> Aggregator
Aggregator
    GROUP_BY = _sort
    ORDERED = No
    LIST_NAME = _list
    ACCUM_ATTRS_NAME = Merge Incoming Attributes
    MODE = Attributes Only
    SEP = ,
    AGGREGATE -> ModuloCounter
ModuloCounter
    MOD = 4
    DOMAIN = modcounter
    CNT_ATTR = _modulo_count
    -> ListExploder
ListExploder
    ATTR_ACCUM_MODE = Merge Incoming List
    ATTR_CONFLICT_RES = Use Incoming List
    INDEX_ATTR = _element_index
    LIST_ATTR = _list{}
    ELEMENTS -> FeatureMerger [REQUESTOR]
    ELEMENTS -> Inspector

Bookmark: Add modulo count attribute to split Ouput File (max. size = 2gb)
Inspector
FeatureMerger
    MERGE_TYPE = Attributes and Geometry
    JOIN_KEYS = @Value(gml_id) @Value(gml_id) AUTO
    REJECT_NULL_MISSING_KEYS = No
    ATTR_CONFLICT_RES = Use Supplier
    SUPPLIERS_FIRST = No
    IGNORE_NULLS = No
    ATTR_ACCUM_MODE = Merge Supplier
    PROCESS_DUPS = No
    MERGED -> AttributeRemover
AttributeRemover
    REMOVE_ATTRS = _sort,_element_index
    -> FeatureTypeFilter
FeatureTypeFilter
    ATTRIBUTES = <BLANK>,Building,RoofSurface,WallSurface,GroundSurface,<UNFILTERED>
    Building -> AttributeEncoder
    RoofSurface -> AttributeEncoder_2
    WallSurface -> AttributeEncoder_3
    GroundSurface -> AttributeEncoder_4

Bookmark: Post processing
AttributeEncoder
    TREAT_AS_BYTES = Honor Encoding
    DEST_ENCODING = fme-system
    ATTRCHOICE = Selected Attributes
    ATTRLIST = externalReference{0}.externalObject.uri externalReference{0}.externalObject.name externalReference{1}.externalObject.name externalReference{1}.informationSystem externalReference{0}.informationSystem
    -> CityGMLGeometrySetter_3
CityGMLGeometrySetter_3
    ROLE = cityObjectMember
    GEOM = lod2MultiSurface
    -> GeometryPropertySetter_3
GeometryPropertySetter_3
    REMOVE_ATTRIBUTE = No
    OVERWRITE_CHOICE = Yes
    SETTYPE_PARAM = Traits From Attributes
    SRC_ATTRS = citygml_lod_name
    SET -> Building (writer CITYGML_3)
    SET -> Building
AttributeEncoder_2
    TREAT_AS_BYTES = Honor Encoding
    DEST_ENCODING = fme-system
    ATTRCHOICE = Selected Attributes
    ATTRLIST = externalReference{0}.externalObject.uri externalReference{0}.externalObject.name externalReference{1}.externalObject.name externalReference{1}.informationSystem externalReference{0}.informationSystem
    -> CityGMLGeometrySetter_2
CityGMLGeometrySetter_2
    ROLE = boundedBy
    GEOM = lod2MultiSurface
    -> GeometryPropertySetter_2
GeometryPropertySetter_2
    REMOVE_ATTRIBUTE = No
    OVERWRITE_CHOICE = Yes
    SETTYPE_PARAM = Traits From Attributes
    SRC_ATTRS = citygml_lod_name
    SET -> RoofSurface (writer CITYGML_3)
    SET -> RoofSurface
AttributeEncoder_3
    TREAT_AS_BYTES = Honor Encoding
    DEST_ENCODING = fme-system
    ATTRCHOICE = Selected Attributes
    ATTRLIST = externalReference{0}.externalObject.uri externalReference{0}.externalObject.name externalReference{1}.externalObject.name externalReference{1}.informationSystem externalReference{0}.informationSystem
    -> CityGMLGeometrySetter_4
CityGMLGeometrySetter_4
    ROLE = boundedBy
    GEOM = lod2MultiSurface
    -> GeometryPropertySetter_4
GeometryPropertySetter_4
    REMOVE_ATTRIBUTE = No
    OVERWRITE_CHOICE = Yes
    SETTYPE_PARAM = Traits From Attributes
    SRC_ATTRS = citygml_lod_name
    SET -> WallSurface (writer CITYGML_3)
    SET -> WallSurface
AttributeEncoder_4
    TREAT_AS_BYTES = Honor Encoding
    DEST_ENCODING = fme-system
    ATTRCHOICE = Selected Attributes
    ATTRLIST = externalReference{0}.externalObject.uri externalReference{0}.externalObject.name externalReference{1}.externalObject.name externalReference{1}.informationSystem externalReference{0}.informationSystem
    -> CityGMLGeometrySetter_5
CityGMLGeometrySetter_5
    ROLE = boundedBy
    GEOM = lod2MultiSurface
    -> GeometryPropertySetter_5
GeometryPropertySetter_5
    REMOVE_ATTRIBUTE = No
    OVERWRITE_CHOICE = Yes
    SETTYPE_PARAM = Traits From Attributes
    SRC_ATTRS = citygml_lod_name
    SET -> GroundSurface (writer CITYGML_3)
    SET -> GroundSurface

Bookmark: Output Data
Building (writer CITYGML_3)
    attributes: Adress_bin xml_buffer, borough_block_lot_number xml_buffer, building_base_area xml_buffer, building_identification_number xml_char(200), building_name_NYC xml_char(200), building_under_construction xml_buffer, building_volume xml_buffer, citygml_class xml_buffer, citygml_feature_role xml_buffer, citygml_function{} xml_buffer, citygml_level_of_detail{} xml_buffer, citygml_level_of_detail{0} xml_char(200), citygml_measured_height xml_real64, citygml_measured_height_units xml_buffer, citygml_roof_type xml_buffer, citygml_storey_heights_above_ground xml_buffer, citygml_storey_heights_above_ground_units xml_buffer, citygml_storey_heights_below_ground xml_buffer, citygml_storey_heights_below_ground_units xml_buffer, citygml_storeys_above_ground xml_uint64, citygml_storeys_below_ground xml_uint64, citygml_target_uri xml_buffer, citygml_usage{} xml_buffer, citygml_year_of_construction xml_buffer, citygml_year_of_demolition xml_buffer, doitt_id xml_buffer, externalReference{}.externalObject.name xml_xml, externalReference{}.externalObject.uri xml_xml, externalReference{}.informationSystem xml_xml, GE_LoD1_zOffset xml_xml,
      geom_source xml_buffer, gml_description xml_buffer, gml_name xml_buffer, ground_elevation xml_buffer, last_modify_date xml_buffer, last_status_1 xml_buffer, last_status_type xml_buffer, OBJECTID xml_buffer, PLUTO_area_source xml_buffer, PLUTO_building_area xml_buffer, PLUTO_building_class xml_buffer, PLUTO_building_depth xml_buffer, PLUTO_building_frontage xml_buffer, PLUTO_built_floor_area_ratio xml_buffer, PLUTO_commercial_area xml_buffer, PLUTO_condominium_number xml_buffer, PLUTO_factory_area xml_buffer, PLUTO_garage_area xml_buffer, PLUTO_land_use_category xml_buffer, PLUTO_lot_address xml_buffer, PLUTO_number_of_floors xml_buffer, PLUTO_office_area xml_buffer, PLUTO_other_area xml_buffer, PLUTO_proximity_code xml_buffer, PLUTO_residential_area xml_buffer, PLUTO_retail_area xml_buffer, PLUTO_storage_area xml_buffer, PLUTO_units_residential xml_buffer, PLUTO_year_altered_1 xml_buffer, PLUTO_year_altered_2 xml_buffer,
      PLUTO_year_built xml_buffer, PLUTO_year_built_code xml_buffer, source_id xml_buffer, status xml_buffer
Building: Inspector
RoofSurface (writer CITYGML_3)
    attributes: building_identification_number xml_char(200), citygml_appearance{}.xlink_href xml_buffer, citygml_creationDate xml_date, citygml_feature_role xml_buffer, citygml_feature_role_attr_name xml_buffer, citygml_feature_role_attr_val xml_buffer, citygml_generalizes_to{}.xlink_href xml_buffer, citygml_level_of_detail{} xml_buffer, citygml_opening{}.xlink_href xml_buffer, citygml_target_uri xml_buffer, citygml_terminationDate xml_date, externalReference{}.externalObject.name xml_xml, externalReference{}.externalObject.uri xml_xml, externalReference{}.informationSystem xml_xml, gml_description xml_xml, gml_name xml_buffer, surface_area_sqm xml_char(200)
RoofSurface: Inspector
WallSurface (writer CITYGML_3)
    attributes: building_identification_number xml_char(200), citygml_appearance{}.xlink_href xml_buffer, citygml_creationDate xml_date, citygml_feature_role xml_buffer, citygml_feature_role_attr_name xml_buffer, citygml_feature_role_attr_val xml_buffer, citygml_generalizes_to{}.xlink_href xml_buffer, citygml_level_of_detail{} xml_buffer, citygml_opening{}.xlink_href xml_buffer, citygml_target_uri xml_buffer, citygml_terminationDate xml_date, externalReference{}.externalObject.name xml_xml, externalReference{}.externalObject.uri xml_xml, externalReference{}.informationSystem xml_xml, gml_description xml_xml, gml_name xml_buffer, surface_area_sqm xml_char(200)
WallSurface: Inspector
GroundSurface (writer CITYGML_3)
    attributes: building_identification_number xml_char(200), citygml_appearance{}.xlink_href xml_buffer, citygml_creationDate xml_date, citygml_feature_role xml_buffer, citygml_feature_role_attr_name xml_buffer, citygml_feature_role_attr_val xml_buffer, citygml_generalizes_to{}.xlink_href xml_buffer, citygml_level_of_detail{} xml_buffer, citygml_opening{}.xlink_href xml_buffer, citygml_target_uri xml_buffer, citygml_terminationDate xml_date, externalReference{}.externalObject.name xml_xml, externalReference{}.externalObject.uri xml_xml, externalReference{}.informationSystem xml_xml, gml_description xml_xml, gml_name xml_buffer, surface_area_sqm xml_char(200)
GroundSurface: Inspector

FME custom transformer CityGMLGeometrySetter
This transformer provides a convenient way to set both the CityGML LOD Name and role from a preset list of options.
Input Ports
    Input
    Features to tag with City LOD name and feature role 
    Output Ports
    Output
    Features tagged with City LOD name and feature role 
    Parameters
    CityGML Lod Name
    Select the desired CityGML Lod name
    Feature Role
    Select the desired feature role

Parameters:
- GEOM =   # CityGML Lod Name
- ROLE =   # Feature Role

Input (input)
    -> AttributeCreator
Note: Set LOD name / and citygml role
AttributeCreator
    ATTR_TABLE:
      SET_TO citygml_lod_name = $(GEOM)
      SET_TO citygml_feature_role = $(ROLE)
    -> GeometryPropertySetter
Note: Convert LOD to geometry trait
GeometryPropertySetter
    GQUERY:
      for $geom in //geometry
      where $geom/count(parent::geometry) = 0
      return number($geom/@fme_id)
    REMOVE_ATTRIBUTE = No
    OVERWRITE_CHOICE = Yes
    SETTYPE_PARAM = Traits From Attributes
    SRC_ATTRS = citygml_lod_name
    SET -> Output (output)
Output (output)
