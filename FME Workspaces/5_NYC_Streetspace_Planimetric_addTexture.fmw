FME workspace 5_NYC_Streetspace_Planimetric_addTexture.fmw

Parameters:
- SourceDataset_JPEG = H:\TUM Geoinformatik\City Model NYC\Datengrundlage\Texture\Roadbed_texture.jpg   # Source JPEG File(s)
- SourceDataset_CITYGML_13 = H:\Masterarbeit\Umsetzung\Datenexport Umsetzung\CityGML\Sidewalk_CityGML\Sidewalk_CityGML.gml   # Source CityGML File(s)
- SourceDataset_JPEG_13 = H:\TUM Geoinformatik\City Model NYC\Datengrundlage\Texture\Plaza_Texture.jpg   # Source JPEG File(s)
- SourceDataset_JPEG_19 = H:\TUM Geoinformatik\City Model NYC\Datengrundlage\Texture\Median_Painted_Texture.jpg   # Source JPEG File(s)
- SourceDataset_JPEG_11 = H:\TUM Geoinformatik\City Model NYC\Datengrundlage\Texture\Curbs_Texture.jpg   # Source JPEG File(s)
- SourceDataset_JPEG_12 = H:\TUM Geoinformatik\City Model NYC\Datengrundlage\Texture\Median_Raised_Texture.JPG   # Source JPEG File(s)
- SourceDataset_JPEG_17 = H:\TUM Geoinformatik\City Model NYC\Datengrundlage\Texture\Track_texture.jpg   # Source JPEG File(s)
- SourceDataset_JPEG_14 = H:\TUM Geoinformatik\City Model NYC\Datengrundlage\Texture\Sidewalk_Texture.jpg   # Source JPEG File(s)
- SourceDataset_JPEG_16 = H:\TUM Geoinformatik\City Model NYC\Datengrundlage\Texture\Grass_Texture.jpg   # Source JPEG File(s)
- SourceDataset_CITYGML = F:\Straßenraummodell Version 2.0\Daten für 3D-Web-Map-Client\CityGML untexturiert neu\Entrance\Road.gml   # Source CityGML File(s)
- SourceDataset_CITYGML_19 = F:\Straßenraummodell Version 2.0\Daten für 3D-Web-Map-Client\CityGML untexturiert neu\Intersection\Road\Road.gml   # Source CityGML File(s)
- SourceDataset_CITYGML_15 = F:\Straßenraummodell Version 2.0\Daten für 3D-Web-Map-Client\CityGML untexturiert neu\Roadbed\Road.gml   # Source CityGML File(s)
- SourceDataset_CITYGML_23 = F:\Straßenraummodell Version 2.0\Daten für 3D-Web-Map-Client\CityGML untexturiert\Sidewalk gesamt\Road.gml   # Source CityGML File(s)
- SourceDataset_CITYGML_17 = F:\Straßenraummodell Version 2.0\Daten für 3D-Web-Map-Client\CityGML untexturiert neu\Median_Painted\Road.gml   # Source CityGML File(s)
- SourceDataset_CITYGML_21 = F:\Straßenraummodell Version 2.0\Daten für 3D-Web-Map-Client\CityGML untexturiert neu\Median_Raised\Road.gml   # Source CityGML File(s)
- SourceDataset_CITYGML_14 = F:\Straßenraummodell Version 2.0\Daten für 3D-Web-Map-Client\CityGML untexturiert neu\Median_Grass\Road.gml   # Source CityGML File(s)
- SourceDataset_CITYGML_16 = F:\Straßenraummodell Version 2.0\Daten für 3D-Web-Map-Client\CityGML untexturiert neu\Parking_Lot\Square.gml   # Source CityGML File(s)
- SourceDataset_CITYGML_18 = F:\Straßenraummodell Version 2.0\Daten für 3D-Web-Map-Client\CityGML untexturiert neu\Plaza\Square.gml   # Source CityGML File(s)
- SourceDataset_CITYGML_20 = F:\Straßenraummodell Version 2.0\Daten für 3D-Web-Map-Client\CityGML untexturiert neu\Track\Track.gml   # Source CityGML File(s)
- SourceDataset_CITYGML_22 = F:\Straßenraummodell Version 2.0\Daten für 3D-Web-Map-Client\CityGML untexturiert\Curb_gesamt\Road.gml   # Source CityGML File(s)

Readers:
- JPEG_1: JPEG from $(SourceDataset_JPEG)
- CITYGML_1: CITYGML from $(SourceDataset_CITYGML_13)
- JPEG_2: JPEG from $(SourceDataset_JPEG_13)
- JPEG_3: JPEG from $(SourceDataset_JPEG_19)
- JPEG_4: JPEG from $(SourceDataset_JPEG_11)
- JPEG_5: JPEG from $(SourceDataset_JPEG_12)
- JPEG_6: JPEG from $(SourceDataset_JPEG_17)
- JPEG_7: JPEG from $(SourceDataset_JPEG_14)
- JPEG_8: JPEG from $(SourceDataset_JPEG_16)
- CITYGML_2: CITYGML from $(SourceDataset_CITYGML)
- CITYGML_3: CITYGML from $(SourceDataset_CITYGML_19)
- CITYGML_4: CITYGML from $(SourceDataset_CITYGML_15)
- CITYGML_5: CITYGML from $(SourceDataset_CITYGML_23)
- CITYGML_6: CITYGML from $(SourceDataset_CITYGML_17)
- CITYGML_7: CITYGML from $(SourceDataset_CITYGML_21)
- CITYGML_8: CITYGML from $(SourceDataset_CITYGML_14)
- CITYGML_9: CITYGML from $(SourceDataset_CITYGML_16)
- CITYGML_10: CITYGML from $(SourceDataset_CITYGML_18)
- CITYGML_11: CITYGML from $(SourceDataset_CITYGML_20)
- CITYGML_12: CITYGML from $(SourceDataset_CITYGML_22)

Bookmark: Untextured Input Data
Road (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, citygml_surfaceMaterial xml_buffer, entrance_adjacent_segmentID xml_buffer, entrance_adjacent_street_name xml_buffer, entrance_area_sqm xml_buffer
    -> Deaggregator_8
Road (reader CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, citygml_surfaceMaterial xml_buffer, construction_status xml_buffer, gml_name{} xml_buffer, intersecting_segements_count xml_buffer, intersecting_segmentIDs_conc xml_buffer, intersecting_street_names_conc xml_buffer,
      intersection_area_sqm xml_buffer, snow_priority xml_buffer, special_address_place_name xml_buffer, special_address_place_name_2 xml_buffer, special_address_place_name_3 xml_buffer, special_address_place_name_4 xml_buffer, special_address_place_name_5 xml_buffer, special_address_type xml_buffer, special_address_type_2 xml_buffer, special_address_type_3 xml_buffer, special_address_type_4 xml_buffer, special_address_type_5 xml_buffer
    -> Deaggregator_7
Road (reader CITYGML_4)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, bike_lane xml_buffer, citygml_surfaceMaterial xml_buffer, construction_status xml_buffer, curve_flag xml_buffer, face_code xml_buffer, level_end_segment xml_buffer,
      level_start_segment xml_buffer, node_id_from xml_buffer, node_id_to xml_buffer, number_parking_lanes xml_buffer, number_total_lanes xml_buffer, number_travel_lanes xml_buffer, orientation xml_buffer, physical_id xml_buffer, radius_arc xml_buffer, sanitation_district_boundary_indicator xml_buffer, segment_count xml_buffer, segment_id xml_buffer, segment_type xml_buffer, sequence_number xml_buffer, slope_percent xml_buffer, snow_priority xml_buffer, special_address_place_name xml_buffer, special_address_place_name_2 xml_buffer, special_address_place_name_3 xml_buffer, special_address_place_name_4 xml_buffer, special_address_place_name_5 xml_buffer, special_address_type xml_buffer, special_address_type_2 xml_buffer, special_address_type_3 xml_buffer, special_address_type_4 xml_buffer, special_address_type_5 xml_buffer, street_area_3D_sqm xml_buffer, street_code xml_buffer, street_length_3D_meter xml_buffer, street_pavement_rating_date xml_buffer,
      street_pavement_rating_num xml_buffer, street_pavement_rating_text xml_buffer, street_speed_limit_km_h xml_buffer, street_speed_limit_mph xml_buffer, street_width_meter xml_buffer, traffic_direction xml_buffer, traffic_direction_source xml_buffer
    -> Deaggregator_10
Road (reader CITYGML_5)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, _modulo_count xml_buffer, citygml_surfaceMaterial xml_buffer, road_id xml_buffer, sidewalk_adjacent_segmentID xml_buffer, sidewalk_adjacent_street_name xml_buffer, sidewalk_area_sqm xml_buffer,
      sidewalk_height_inch xml_buffer, sidewalk_height_meter xml_buffer, sidewalk_volume_cubicmeter xml_buffer, surfaceType xml_buffer
    -> Deaggregator_2
Road (reader CITYGML_12)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, _modulo_count xml_buffer, citygml_surfaceMaterial xml_buffer, curb_adjacent_segmentID xml_buffer, curb_area_sqm xml_buffer, curb_height_inch xml_buffer, curb_height_meter xml_buffer,
      curb_volume_cubicmeter xml_buffer, externalReference{}.informationSystem  xml_buffer, road_id xml_buffer, surfaceType xml_buffer
    -> Deaggregator_3
Road (reader CITYGML_6)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, citygml_surfaceMaterial xml_buffer, median_area_sqm xml_buffer
    -> AppearanceSetter_6 [GEOMETRY]
Road (reader CITYGML_7)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, citygml_surfaceMaterial xml_buffer, median_area_sqm xml_buffer, median_height_inch xml_buffer, median_height_meter xml_buffer, median_volume_cubicmeter xml_buffer
    -> Deaggregator_4
Road (reader CITYGML_8)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, citygml_surface_material xml_buffer, median_area_sqm xml_buffer, median_height_inch xml_buffer, median_height_meter xml_buffer
    -> Deaggregator_6
Square (reader CITYGML_9)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, citygml_surface_material xml_buffer, parking_lot_area_sqm xml_buffer, parking_lot_entrance_street_names xml_buffer
    -> Deaggregator_11
Square (reader CITYGML_10)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, citygml_surfaceMaterial xml_buffer, plaza_area_sqm xml_buffer, plaza_height_inch xml_buffer, plaza_height_meter xml_buffer, plaza_volume_cubicmeter xml_buffer, surfaceType xml_buffer
    -> Deaggregator
Track (reader CITYGML_11)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, citygml_surface_material xml_buffer, sidewalk_height_inch xml_buffer, sidewalk_height_meter xml_buffer
    -> Deaggregator_5

Bookmark: Entrance Texture
Deaggregator_8
    SPLIT_COMPOSITES = Yes
    GEOM_NAME_FIELD = _geometry_name
    MODE = Flatten One Level
    PART_NUMBER_FIELD = _part_number
    EXPLODE_INSTANCES = No
    LIST_ATTR_MODE_LOOKUP = LEAN
    DEAGGREGATED -> AppearanceSetter_11 [GEOMETRY]
AppearanceStyler_11
    ALPHA = 1.0
    TEXTURE_CENTER_U = 0.0
    TEXTURE_ROTATION_ANGLE = 0.0
    TEXTURE_U_SHEARING_FACTOR = 0.0
    TEXTURE_U_OFFSET = 0.0
    TEXTURE_CENTER_V = 0.0
    TEXTURE_V_SCALING_FACTOR = 1.0
    TEXTURE_WRAP_DISPLAY = Repeat in U and V
    TEXTURE_V_OFFSET = 0.0
    DIFFUSE_COLOR = 1,1,1
    TEXTURE_V_SHEARING_FACTOR = 0.0
    TEXTURE_U_SCALING_FACTOR = 1.0
    -> AppearanceSetter_11 [APPEARANCE]
AppearanceSetter_11
    GQUERY:
      for $geom in //geometry
      where $geom/count(parent::geometry) = 0
      return number($geom/@fme_id)
    TEXTURE_U_OFFSET2 = 0.0
    SET_ON_SIDE = Front Side
    TEXTURE_WRAP_DISPLAY = Repeat in U and V
    TEXTURE_V_SCALE_FACTOR = 1.0
    TEXTURE_U_SCALING_FACTOR = 0.1
    USE_EXISTING_TEXTURE_COORDINATES = Yes
    TEXTURE_V_OFFSET2 = 0.0
    TEXTURE_U_SCALE_FACTOR = 1.0
    TEXTURE_V_SCALING_FACTOR = 0.1
    DEF_STORAGE = Create New Definitions
    TEXTURE_MAPPING_TYPE_CHOICE = From Top View
    -> Aggregator_10
Aggregator_10
    ORDERED = No
    SEP = ,
    AGGREGATE_TYPE = Homogeneous Collection (If Possible)
    MODE = Geometry - Assemble One Level
    GROUP_BY = gml_id
    ACCUM_ATTRS_NAME = Get Attributes From One Representative Feature
    AGGREGATE -> AttributeRemover_11
AttributeRemover_11
    REMOVE_ATTRS = _part_number,_geometry_name,_hierarchy_id,orientation,_hierarchy_child_id_list{0},_hierarchy_parent_id
    -> CityGMLGeometrySetter_11
CityGMLGeometrySetter_11
    GEOM = lod3MultiSurface
    ROLE = trafficArea
    -> GeometryPropertySetter_11
GeometryPropertySetter_11
    REMOVE_ATTRIBUTE = No
    SRC_ATTRS = citygml_level_of_detail{0} citygml_feature_role citygml_lod_name
    SETTYPE_PARAM = Traits From Attributes
    OVERWRITE_CHOICE = Yes
    SET -> Entrance
Entrance: Inspector

Bookmark: Intersection Texture
Deaggregator_7
    SPLIT_COMPOSITES = Yes
    GEOM_NAME_FIELD = _geometry_name
    MODE = Flatten One Level
    PART_NUMBER_FIELD = _part_number
    EXPLODE_INSTANCES = No
    LIST_ATTR_MODE_LOOKUP = LEAN
    DEAGGREGATED -> AppearanceSetter_10 [GEOMETRY]
AppearanceStyler_10
    ALPHA = 1.0
    TEXTURE_CENTER_U = 0.0
    TEXTURE_ROTATION_ANGLE = 0.0
    TEXTURE_U_SHEARING_FACTOR = 0.0
    TEXTURE_U_OFFSET = 0.0
    TEXTURE_CENTER_V = 0.0
    TEXTURE_V_SCALING_FACTOR = 1.0
    TEXTURE_WRAP_DISPLAY = Repeat in U and V
    TEXTURE_V_OFFSET = 0.0
    DIFFUSE_COLOR = 1,1,1
    TEXTURE_V_SHEARING_FACTOR = 0.0
    TEXTURE_U_SCALING_FACTOR = 1.0
    -> AppearanceSetter_10 [APPEARANCE]
AppearanceSetter_10
    GQUERY:
      for $geom in //geometry
      where $geom/count(parent::geometry) = 0
      return number($geom/@fme_id)
    TEXTURE_U_OFFSET2 = 0.0
    SET_ON_SIDE = Front Side
    TEXTURE_WRAP_DISPLAY = Repeat in U and V
    TEXTURE_V_SCALE_FACTOR = 1.0
    TEXTURE_U_SCALING_FACTOR = 0.1
    USE_EXISTING_TEXTURE_COORDINATES = Yes
    TEXTURE_V_OFFSET2 = 0.0
    TEXTURE_U_SCALE_FACTOR = 1.0
    TEXTURE_V_SCALING_FACTOR = 0.1
    DEF_STORAGE = Create New Definitions
    TEXTURE_MAPPING_TYPE_CHOICE = From Top View
    -> Aggregator_9
Aggregator_9
    ORDERED = No
    SEP = ,
    AGGREGATE_TYPE = Homogeneous Collection (If Possible)
    MODE = Geometry - Assemble One Level
    GROUP_BY = gml_id
    ACCUM_ATTRS_NAME = Get Attributes From One Representative Feature
    AGGREGATE -> AttributeRemover_10
AttributeRemover_10
    REMOVE_ATTRS = _part_number,_geometry_name,_hierarchy_id,orientation,_hierarchy_child_id_list{0},_hierarchy_parent_id
    -> CityGMLGeometrySetter_10
CityGMLGeometrySetter_10
    GEOM = lod3MultiSurface
    ROLE = trafficArea
    -> GeometryPropertySetter_10
GeometryPropertySetter_10
    REMOVE_ATTRIBUTE = No
    SRC_ATTRS = citygml_level_of_detail{0} citygml_feature_role citygml_lod_name
    SETTYPE_PARAM = Traits From Attributes
    OVERWRITE_CHOICE = Yes
    SET -> Intersection
Intersection: Inspector

Bookmark: Roadbed Texture
Deaggregator_10
    SPLIT_COMPOSITES = Yes
    GEOM_NAME_FIELD = _geometry_name
    MODE = Flatten One Level
    PART_NUMBER_FIELD = _part_number
    EXPLODE_INSTANCES = No
    LIST_ATTR_MODE_LOOKUP = LEAN
    DEAGGREGATED -> AppearanceSetter [GEOMETRY]
JPEG (reader JPEG_1)
    -> AppearanceStyler
    -> AppearanceStyler_10
    -> AppearanceStyler_11
    -> AppearanceStyler_5
AppearanceStyler
    ALPHA = 1.0
    TEXTURE_CENTER_U = 0.0
    TEXTURE_ROTATION_ANGLE = 0.0
    TEXTURE_U_SHEARING_FACTOR = 0.0
    TEXTURE_U_OFFSET = 0.0
    TEXTURE_CENTER_V = 0.0
    TEXTURE_V_SCALING_FACTOR = 1.0
    TEXTURE_WRAP_DISPLAY = Repeat in U and V
    TEXTURE_V_OFFSET = 0.0
    DIFFUSE_COLOR = 1,1,1
    TEXTURE_V_SHEARING_FACTOR = 0.0
    TEXTURE_U_SCALING_FACTOR = 1.0
    -> AppearanceSetter [APPEARANCE]
AppearanceSetter
    GQUERY:
      for $geom in //geometry
      where $geom/count(parent::geometry) = 0
      return number($geom/@fme_id)
    TEXTURE_U_OFFSET2 = 0.0
    SET_ON_SIDE = Front Side
    TEXTURE_WRAP_DISPLAY = Repeat in U and V
    TEXTURE_V_SCALE_FACTOR = 1.0
    TEXTURE_U_SCALING_FACTOR = 0.1
    USE_EXISTING_TEXTURE_COORDINATES = Yes
    TEXTURE_V_OFFSET2 = 0.0
    TEXTURE_U_SCALE_FACTOR = 1.0
    TEXTURE_V_SCALING_FACTOR = 0.1
    DEF_STORAGE = Create New Definitions
    TEXTURE_MAPPING_TYPE_CHOICE = From Top View
    -> Aggregator_6
Aggregator_6
    ORDERED = No
    SEP = ,
    AGGREGATE_TYPE = Homogeneous Collection (If Possible)
    MODE = Geometry - Assemble One Level
    GROUP_BY = gml_id
    ACCUM_ATTRS_NAME = Get Attributes From One Representative Feature
    AGGREGATE -> AttributeRemover_5
AttributeRemover_5
    REMOVE_ATTRS = _part_number,_geometry_name,_hierarchy_id,orientation,_hierarchy_child_id_list{0},_hierarchy_parent_id
    -> CityGMLGeometrySetter
CityGMLGeometrySetter
    GEOM = lod3MultiSurface
    ROLE = trafficArea
    -> GeometryPropertySetter
GeometryPropertySetter
    REMOVE_ATTRIBUTE = No
    SRC_ATTRS = citygml_level_of_detail{0} citygml_feature_role citygml_lod_name
    SETTYPE_PARAM = Traits From Attributes
    OVERWRITE_CHOICE = Yes
    SET -> Roadbed
Roadbed: Inspector

Bookmark: Sidewalk Texture
Deaggregator_2
    SPLIT_COMPOSITES = No
    GEOM_NAME_FIELD = _geometry_name
    MODE = Flatten One Level
    PART_NUMBER_FIELD = _part_number
    EXPLODE_INSTANCES = No
    LIST_ATTR_MODE_LOOKUP = LEAN
    DEAGGREGATED -> AppearanceSetter_2 [GEOMETRY]
JPEG (reader JPEG_7)
    -> AppearanceStyler_2
AppearanceStyler_2
    ALPHA = 1.0
    TEXTURE_CENTER_U = 0.0
    TEXTURE_ROTATION_ANGLE = 0.0
    TEXTURE_U_SHEARING_FACTOR = 0.0
    TEXTURE_U_OFFSET = 0.0
    TEXTURE_CENTER_V = 0.0
    TEXTURE_V_SCALING_FACTOR = 1.0
    TEXTURE_WRAP_DISPLAY = Repeat in U and V
    TEXTURE_V_OFFSET = 0.0
    DIFFUSE_COLOR = 1,1,1
    TEXTURE_V_SHEARING_FACTOR = 0.0
    TEXTURE_U_SCALING_FACTOR = 1.0
    -> AppearanceSetter_2 [APPEARANCE]
AppearanceSetter_2
    GQUERY:
      for $geom in //geometry
      where $geom/count(parent::geometry) = 0
      return number($geom/@fme_id)
    TEXTURE_U_OFFSET2 = 0.0
    SET_ON_SIDE = Front Side
    TEXTURE_WRAP_DISPLAY = Repeat in U and V
    TEXTURE_V_SCALE_FACTOR = 1.0
    TEXTURE_U_SCALING_FACTOR = 0.1
    USE_EXISTING_TEXTURE_COORDINATES = Yes
    TEXTURE_V_OFFSET2 = 0.0
    TEXTURE_U_SCALE_FACTOR = 1.0
    TEXTURE_V_SCALING_FACTOR = 0.1
    DEF_STORAGE = Create New Definitions
    TEXTURE_MAPPING_TYPE_CHOICE = From Top View
    -> Aggregator_2
Aggregator_2
    ORDERED = No
    SEP = ,
    AGGREGATE_TYPE = Homogeneous Collection (If Possible)
    MODE = Geometry - Assemble One Level
    GROUP_BY = gml_id
    ACCUM_ATTRS_NAME = Get Attributes From One Representative Feature
    AGGREGATE -> AttributeRemover_4
AttributeRemover_4
    REMOVE_ATTRS = _geometry_name,_part_number
    -> CityGMLGeometrySetter_9
CityGMLGeometrySetter_9
    GEOM = lod3MultiSurface
    ROLE = trafficArea
    -> GeometryPropertySetter_9
GeometryPropertySetter_9
    REMOVE_ATTRIBUTE = No
    SRC_ATTRS = citygml_level_of_detail{0} citygml_feature_role citygml_lod_name
    SETTYPE_PARAM = Traits From Attributes
    OVERWRITE_CHOICE = Yes
    SET -> Sidewalk
Sidewalk: Inspector

Bookmark: Curbs Texture
Deaggregator_3
    COPY_ATTR = Every Node
    SPLIT_COMPOSITES = No
    ID_ATTR = _hierarchy_id
    GEOM_NAME_FIELD = _geometry_name
    PARENT_ID_ATTR = _hierarchy_parent_id
    ID_SELECTION = ID and Parent ID
    CHILD_ID_ATTR = _hierarchy_child_id_list
    MODE = Flatten One Level
    PART_NUMBER_FIELD = _part_number
    EXPLODE_INSTANCES = No
    LIST_ATTR_MODE_LOOKUP = LEAN
    DEAGGREGATED -> AppearanceSetter_4 [GEOMETRY]
JPEG (reader JPEG_4)
    -> AppearanceStyler_4
AppearanceStyler_4
    ALPHA = 1.0
    TEXTURE_CENTER_U = 0.0
    TEXTURE_ROTATION_ANGLE = 0.0
    TEXTURE_U_SHEARING_FACTOR = 0.0
    TEXTURE_U_OFFSET = 0.0
    TEXTURE_CENTER_V = 0.0
    TEXTURE_V_SCALING_FACTOR = 1.0
    TEXTURE_WRAP_DISPLAY = Repeat in U and V
    TEXTURE_V_OFFSET = 0.0
    DIFFUSE_COLOR = 1,1,1
    TEXTURE_V_SHEARING_FACTOR = 0.0
    TEXTURE_U_SCALING_FACTOR = 1.0
    -> AppearanceSetter_4 [APPEARANCE]
AppearanceSetter_4
    GQUERY:
      for $geom in //geometry
      where $geom/count(parent::geometry) = 0
      return number($geom/@fme_id)
    TEXTURE_U_OFFSET2 = 0.0
    SET_ON_SIDE = Front Side
    TEXTURE_WRAP_DISPLAY = Repeat in U and V
    TEXTURE_V_SCALE_FACTOR = 1.0
    TEXTURE_U_SCALING_FACTOR = 0.2
    USE_EXISTING_TEXTURE_COORDINATES = Yes
    TEXTURE_V_OFFSET2 = 0.0
    TEXTURE_U_SCALE_FACTOR = 1.0
    TEXTURE_V_SCALING_FACTOR = 0.2
    DEF_STORAGE = Create New Definitions
    TEXTURE_MAPPING_TYPE_CHOICE = From Top View
    -> Aggregator_3
Aggregator_3
    ORDERED = No
    SEP = ,
    AGGREGATE_TYPE = Homogeneous Collection (If Possible)
    MODE = Geometry - Assemble One Level
    GROUP_BY = gml_id
    ACCUM_ATTRS_NAME = Get Attributes From One Representative Feature
    AGGREGATE -> AttributeRemover_3
AttributeRemover_3
    REMOVE_ATTRS = _hierarchy_child_id_list{0},_part_number,_ymin,_geometry_name,_hierarchy_id,_ymax,_zmin,_xmin,_zmax,_hierarchy_parent_id,_xmax
    -> CityGMLGeometrySetter_2
CityGMLGeometrySetter_2
    GEOM = lod3MultiSurface
    ROLE = auxiliaryTrafficArea
    -> GeometryPropertySetter_2
GeometryPropertySetter_2
    REMOVE_ATTRIBUTE = No
    SRC_ATTRS = citygml_level_of_detail{0} citygml_feature_role citygml_lod_name
    SETTYPE_PARAM = Traits From Attributes
    OVERWRITE_CHOICE = Yes
    SET -> Curbs
Curbs: Inspector

Bookmark: Raised
Deaggregator_4
    SPLIT_COMPOSITES = No
    GEOM_NAME_FIELD = _geometry_name
    MODE = Flatten One Level
    PART_NUMBER_FIELD = _part_number
    EXPLODE_INSTANCES = No
    LIST_ATTR_MODE_LOOKUP = LEAN
    DEAGGREGATED -> AppearanceSetter_7 [GEOMETRY]
JPEG (reader JPEG_5)
    -> AppearanceStyler_7
AppearanceStyler_7
    ALPHA = 1.0
    TEXTURE_CENTER_U = 0.0
    TEXTURE_ROTATION_ANGLE = 0.0
    TEXTURE_U_SHEARING_FACTOR = 0.0
    TEXTURE_U_OFFSET = 0.0
    TEXTURE_CENTER_V = 0.0
    TEXTURE_V_SCALING_FACTOR = 1.0
    TEXTURE_WRAP_DISPLAY = Repeat in U and V
    TEXTURE_V_OFFSET = 0.0
    DIFFUSE_COLOR = 1,1,1
    TEXTURE_V_SHEARING_FACTOR = 0.0
    TEXTURE_U_SCALING_FACTOR = 1.0
    -> AppearanceSetter_7 [APPEARANCE]
AppearanceSetter_7
    GQUERY:
      for $geom in //geometry
      where $geom/count(parent::geometry) = 0
      return number($geom/@fme_id)
    TEXTURE_U_OFFSET2 = 0.0
    SET_ON_SIDE = Front Side
    TEXTURE_WRAP_DISPLAY = Repeat in U and V
    TEXTURE_V_SCALE_FACTOR = 1.0
    TEXTURE_U_SCALING_FACTOR = 0.2
    USE_EXISTING_TEXTURE_COORDINATES = Yes
    TEXTURE_V_OFFSET2 = 0.0
    TEXTURE_U_SCALE_FACTOR = 1.0
    TEXTURE_V_SCALING_FACTOR = 0.2
    DEF_STORAGE = Create New Definitions
    TEXTURE_MAPPING_TYPE_CHOICE = From Top View
    -> Aggregator_4
Aggregator_4
    ORDERED = No
    SEP = ,
    AGGREGATE_TYPE = Homogeneous Collection (If Possible)
    MODE = Geometry - Assemble One Level
    GROUP_BY = gml_id
    ACCUM_ATTRS_NAME = Get Attributes From One Representative Feature
    AGGREGATE -> AttributeRemover_2
AttributeRemover_2
    REMOVE_ATTRS = _part_number,_ymin,_geometry_name,_ymax,_zmin,_xmin,_zmax,_xmax
    -> CityGMLGeometrySetter_6
CityGMLGeometrySetter_6
    GEOM = lod3MultiSurface
    ROLE = auxiliaryTrafficArea
    -> GeometryPropertySetter_6
GeometryPropertySetter_6
    REMOVE_ATTRIBUTE = No
    SRC_ATTRS = citygml_level_of_detail{0} citygml_feature_role citygml_lod_name
    SETTYPE_PARAM = Traits From Attributes
    OVERWRITE_CHOICE = Yes
    SET -> Median_Raised
Median_Raised: Inspector

Bookmark: Grass
Deaggregator_6
    SPLIT_COMPOSITES = No
    GEOM_NAME_FIELD = _geometry_name
    MODE = Flatten One Level
    PART_NUMBER_FIELD = _part_number
    EXPLODE_INSTANCES = No
    LIST_ATTR_MODE_LOOKUP = LEAN
    DEAGGREGATED -> AppearanceSetter_9 [GEOMETRY]
JPEG (reader JPEG_8)
    -> AppearanceStyler_9
AppearanceStyler_9
    ALPHA = 1.0
    TEXTURE_CENTER_U = 0.0
    TEXTURE_ROTATION_ANGLE = 0.0
    TEXTURE_U_SHEARING_FACTOR = 0.0
    TEXTURE_U_OFFSET = 0.0
    TEXTURE_CENTER_V = 0.0
    TEXTURE_V_SCALING_FACTOR = 1.0
    TEXTURE_WRAP_DISPLAY = Repeat in U and V
    TEXTURE_V_OFFSET = 0.0
    DIFFUSE_COLOR = 1,1,1
    TEXTURE_V_SHEARING_FACTOR = 0.0
    TEXTURE_U_SCALING_FACTOR = 1.0
    -> AppearanceSetter_9 [APPEARANCE]
AppearanceSetter_9
    GQUERY:
      for $geom in //geometry
      where $geom/count(parent::geometry) = 0
      return number($geom/@fme_id)
    TEXTURE_U_OFFSET2 = 0.0
    SET_ON_SIDE = Front Side
    TEXTURE_WRAP_DISPLAY = Repeat in U and V
    TEXTURE_V_SCALE_FACTOR = 1.0
    TEXTURE_U_SCALING_FACTOR = 0.2
    USE_EXISTING_TEXTURE_COORDINATES = Yes
    TEXTURE_V_OFFSET2 = 0.0
    TEXTURE_U_SCALE_FACTOR = 1.0
    TEXTURE_V_SCALING_FACTOR = 0.2
    DEF_STORAGE = Create New Definitions
    TEXTURE_MAPPING_TYPE_CHOICE = From Top View
    -> Aggregator_8
Aggregator_8
    ORDERED = No
    SEP = ,
    AGGREGATE_TYPE = Homogeneous Collection (If Possible)
    MODE = Geometry - Assemble One Level
    GROUP_BY = gml_id
    ACCUM_ATTRS_NAME = Get Attributes From One Representative Feature
    AGGREGATE -> AttributeRemover_9
AttributeRemover_9
    REMOVE_ATTRS = _geometry_name,_part_number
    -> CityGMLGeometrySetter_7
CityGMLGeometrySetter_7
    GEOM = lod3MultiSurface
    ROLE = auxiliaryTrafficArea
    -> GeometryPropertySetter_7
GeometryPropertySetter_7
    REMOVE_ATTRIBUTE = No
    SRC_ATTRS = citygml_level_of_detail{0} citygml_feature_role citygml_lod_name
    SETTYPE_PARAM = Traits From Attributes
    OVERWRITE_CHOICE = Yes
    SET -> Median_Grass
Median_Grass: Inspector

Bookmark: Parking_Lot Texture
Deaggregator_11
    SPLIT_COMPOSITES = Yes
    GEOM_NAME_FIELD = _geometry_name
    MODE = Flatten One Level
    PART_NUMBER_FIELD = _part_number
    EXPLODE_INSTANCES = No
    LIST_ATTR_MODE_LOOKUP = LEAN
    DEAGGREGATED -> AppearanceSetter_5 [GEOMETRY]
AppearanceStyler_5
    ALPHA = 1.0
    TEXTURE_CENTER_U = 0.0
    TEXTURE_ROTATION_ANGLE = 0.0
    TEXTURE_U_SHEARING_FACTOR = 0.0
    TEXTURE_U_OFFSET = 0.0
    TEXTURE_CENTER_V = 0.0
    TEXTURE_V_SCALING_FACTOR = 1.0
    TEXTURE_WRAP_DISPLAY = Repeat in U and V
    TEXTURE_V_OFFSET = 0.0
    DIFFUSE_COLOR = 1,1,1
    TEXTURE_V_SHEARING_FACTOR = 0.0
    TEXTURE_U_SCALING_FACTOR = 1.0
    -> AppearanceSetter_5 [APPEARANCE]
AppearanceSetter_5
    GQUERY:
      for $geom in //geometry
      where $geom/count(parent::geometry) = 0
      return number($geom/@fme_id)
    TEXTURE_U_OFFSET2 = 0.0
    SET_ON_SIDE = Front Side
    TEXTURE_WRAP_DISPLAY = Repeat in U and V
    TEXTURE_V_SCALE_FACTOR = 1.0
    TEXTURE_U_SCALING_FACTOR = 0.2
    USE_EXISTING_TEXTURE_COORDINATES = Yes
    TEXTURE_V_OFFSET2 = 0.0
    TEXTURE_U_SCALE_FACTOR = 1.0
    TEXTURE_V_SCALING_FACTOR = 0.2
    DEF_STORAGE = Create New Definitions
    TEXTURE_MAPPING_TYPE_CHOICE = From Top View
    -> Aggregator_7
Aggregator_7
    ORDERED = No
    SEP = ,
    AGGREGATE_TYPE = Homogeneous Collection (If Possible)
    MODE = Geometry - Assemble One Level
    GROUP_BY = gml_id
    ACCUM_ATTRS_NAME = Get Attributes From One Representative Feature
    AGGREGATE -> AttributeRemover_8
AttributeRemover_8
    REMOVE_ATTRS = _geometry_name,_part_number
    -> CityGMLGeometrySetter_8
CityGMLGeometrySetter_8
    GEOM = lod3MultiSurface
    ROLE = trafficArea
    -> GeometryPropertySetter_8
GeometryPropertySetter_8
    REMOVE_ATTRIBUTE = No
    SRC_ATTRS = citygml_level_of_detail{0} citygml_feature_role citygml_lod_name
    SETTYPE_PARAM = Traits From Attributes
    OVERWRITE_CHOICE = Yes
    SET -> Parking_Lot
Parking_Lot: Inspector

Bookmark: Plaza Texture
Deaggregator
    SPLIT_COMPOSITES = No
    GEOM_NAME_FIELD = _geometry_name
    MODE = Flatten One Level
    PART_NUMBER_FIELD = _part_number
    EXPLODE_INSTANCES = No
    LIST_ATTR_MODE_LOOKUP = LEAN
    DEAGGREGATED -> AppearanceSetter_3 [GEOMETRY]
JPEG (reader JPEG_2)
    -> AppearanceStyler_3
AppearanceStyler_3
    ALPHA = 1.0
    TEXTURE_CENTER_U = 0.0
    TEXTURE_ROTATION_ANGLE = 0.0
    TEXTURE_U_SHEARING_FACTOR = 0.0
    TEXTURE_U_OFFSET = 0.0
    TEXTURE_CENTER_V = 0.0
    TEXTURE_V_SCALING_FACTOR = 1.0
    TEXTURE_WRAP_DISPLAY = Repeat in U and V
    TEXTURE_V_OFFSET = 0.0
    DIFFUSE_COLOR = 1,1,1
    TEXTURE_V_SHEARING_FACTOR = 0.0
    TEXTURE_U_SCALING_FACTOR = 1.0
    -> AppearanceSetter_3 [APPEARANCE]
AppearanceSetter_3
    GQUERY:
      for $geom in //geometry
      where $geom/count(parent::geometry) = 0
      return number($geom/@fme_id)
    TEXTURE_U_OFFSET2 = 0.0
    SET_ON_SIDE = Front Side
    TEXTURE_WRAP_DISPLAY = Repeat in U and V
    TEXTURE_V_SCALE_FACTOR = 1.0
    TEXTURE_U_SCALING_FACTOR = 0.1
    USE_EXISTING_TEXTURE_COORDINATES = No
    TEXTURE_V_OFFSET2 = 0.0
    TEXTURE_U_SCALE_FACTOR = 1.0
    TEXTURE_V_SCALING_FACTOR = 0.1
    DEF_STORAGE = Create New Definitions
    TEXTURE_MAPPING_TYPE_CHOICE = From Top View
    -> Aggregator
Aggregator
    ORDERED = No
    SEP = ,
    AGGREGATE_TYPE = Homogeneous Collection (If Possible)
    MODE = Geometry - Assemble One Level
    GROUP_BY = gml_id
    ACCUM_ATTRS_NAME = Get Attributes From One Representative Feature
    AGGREGATE -> AttributeRemover
AttributeRemover
    REMOVE_ATTRS = _geometry_name,_part_number
    -> Plaza
    -> CityGMLGeometrySetter_4
CityGMLGeometrySetter_4
    GEOM = lod3MultiSurface
    ROLE = trafficArea
    -> GeometryPropertySetter_4
GeometryPropertySetter_4
    REMOVE_ATTRIBUTE = No
    SRC_ATTRS = citygml_level_of_detail{0} citygml_feature_role citygml_lod_name
    SETTYPE_PARAM = Traits From Attributes
    OVERWRITE_CHOICE = Yes
Plaza: Inspector

Bookmark: Track Texture
Deaggregator_5
    SPLIT_COMPOSITES = Yes
    GEOM_NAME_FIELD = _geometry_name
    MODE = Flatten One Level
    PART_NUMBER_FIELD = _part_number
    EXPLODE_INSTANCES = No
    LIST_ATTR_MODE_LOOKUP = LEAN
    DEAGGREGATED -> AppearanceSetter_8 [GEOMETRY]
JPEG (reader JPEG_6)
    -> AppearanceStyler_8
AppearanceStyler_8
    ALPHA = 1.0
    TEXTURE_CENTER_U = 0.0
    TEXTURE_ROTATION_ANGLE = 0.0
    TEXTURE_U_SHEARING_FACTOR = 0.0
    TEXTURE_U_OFFSET = 0.0
    TEXTURE_CENTER_V = 0.0
    TEXTURE_V_SCALING_FACTOR = 1.0
    TEXTURE_WRAP_DISPLAY = Repeat in U and V
    TEXTURE_V_OFFSET = 0.0
    DIFFUSE_COLOR = 1,1,1
    TEXTURE_V_SHEARING_FACTOR = 0.0
    TEXTURE_U_SCALING_FACTOR = 1.0
    -> AppearanceSetter_8 [APPEARANCE]
AppearanceSetter_8
    GQUERY:
      for $geom in //geometry
      where $geom/count(parent::geometry) = 0
      return number($geom/@fme_id)
    TEXTURE_U_OFFSET2 = 0.0
    SET_ON_SIDE = Front Side
    TEXTURE_WRAP_DISPLAY = Repeat in U and V
    TEXTURE_V_SCALE_FACTOR = 1.0
    TEXTURE_U_SCALING_FACTOR = 0.1
    USE_EXISTING_TEXTURE_COORDINATES = Yes
    TEXTURE_V_OFFSET2 = 0.0
    TEXTURE_U_SCALE_FACTOR = 1.0
    TEXTURE_V_SCALING_FACTOR = 0.1
    DEF_STORAGE = Create New Definitions
    TEXTURE_MAPPING_TYPE_CHOICE = From Top View
    -> Aggregator_5
Aggregator_5
    ORDERED = No
    SEP = ,
    AGGREGATE_TYPE = Homogeneous Collection (If Possible)
    MODE = Geometry - Assemble One Level
    GROUP_BY = gml_id
    ACCUM_ATTRS_NAME = Get Attributes From One Representative Feature
    AGGREGATE -> AttributeRemover_6
AttributeRemover_6
    REMOVE_ATTRS = _part_number,_ymin,_geometry_name,_ymax,_zmin,_xmin,_zmax,_xmax
    -> CityGMLGeometrySetter_3
CityGMLGeometrySetter_3
    GEOM = lod3MultiSurface
    ROLE = trafficArea
    -> GeometryPropertySetter_3
GeometryPropertySetter_3
    REMOVE_ATTRIBUTE = No
    SRC_ATTRS = citygml_level_of_detail{0} citygml_feature_role citygml_lod_name
    SETTYPE_PARAM = Traits From Attributes
    OVERWRITE_CHOICE = Yes
    SET -> Track
Track: Inspector

Bookmark: Painted
JPEG (reader JPEG_3)
    -> AppearanceStyler_6
AppearanceStyler_6
    ALPHA = 1.0
    TEXTURE_CENTER_U = 0.0
    TEXTURE_ROTATION_ANGLE = 0.0
    TEXTURE_U_SHEARING_FACTOR = 0.0
    TEXTURE_U_OFFSET = 0.0
    TEXTURE_CENTER_V = 0.0
    TEXTURE_V_SCALING_FACTOR = 1.0
    TEXTURE_WRAP_DISPLAY = Repeat in U and V
    TEXTURE_V_OFFSET = 0.0
    DIFFUSE_COLOR = 1,1,1
    TEXTURE_V_SHEARING_FACTOR = 0.0
    TEXTURE_U_SCALING_FACTOR = 1.0
    -> AppearanceSetter_6 [APPEARANCE]
AppearanceSetter_6
    GQUERY:
      for $geom in //geometry
      where $geom/count(parent::geometry) = 0
      return number($geom/@fme_id)
    TEXTURE_U_OFFSET2 = 0.0
    SET_ON_SIDE = Front Side
    TEXTURE_WRAP_DISPLAY = Repeat in U and V
    TEXTURE_V_SCALE_FACTOR = 1.0
    TEXTURE_U_SCALING_FACTOR = 0.2
    USE_EXISTING_TEXTURE_COORDINATES = Yes
    TEXTURE_V_OFFSET2 = 0.0
    TEXTURE_U_SCALE_FACTOR = 1.0
    TEXTURE_V_SCALING_FACTOR = 0.2
    DEF_STORAGE = Create New Definitions
    TEXTURE_MAPPING_TYPE_CHOICE = From Top View
    -> AttributeRemover_7
AttributeRemover_7
    REMOVE_ATTRS = _part_number,_ymin,_geometry_name,_ymax,_zmin,_xmin,_zmax,_xmax
    -> CityGMLGeometrySetter_5
CityGMLGeometrySetter_5
    GEOM = lod3MultiSurface
    ROLE = auxiliaryTrafficArea
    -> GeometryPropertySetter_5
GeometryPropertySetter_5
    REMOVE_ATTRIBUTE = No
    SRC_ATTRS = citygml_level_of_detail{0} citygml_feature_role citygml_lod_name
    SETTYPE_PARAM = Traits From Attributes
    OVERWRITE_CHOICE = Yes
    SET -> Median_Painted
Median_Painted: Inspector

FME custom transformer CityGMLGeometrySetter
This transformer provides a convenient way to set both the CityGML LOD Name and role from a preset list of options.
Input Ports
    Input
    Features to tag with City LOD name and feature role 
    Output Ports
    Output
    Features tagged with City LOD name and feature role 
    Parameters
    CityGML Lod Name
    Select the desired CityGML Lod name
    Feature Role
    Select the desired feature role

Parameters:
- GEOM =   # CityGML Lod Name
- ROLE =   # Feature Role

INPUT (input)
    -> AttributeCreator
Note: Set LOD name / and citygml role
AttributeCreator
    ATTR_TABLE:
      SET_TO citygml_lod_name = $(GEOM)
      SET_TO citygml_feature_role = $(ROLE)
    -> GeometryPropertySetter
Note: Convert LOD to geometry trait
GeometryPropertySetter
    REMOVE_ATTRIBUTE = No
    SRC_ATTRS = citygml_lod_name
    SETTYPE_PARAM = Traits From Attributes
    OVERWRITE_CHOICE = Yes
    SET -> OUTPUT (output)
OUTPUT (output)
