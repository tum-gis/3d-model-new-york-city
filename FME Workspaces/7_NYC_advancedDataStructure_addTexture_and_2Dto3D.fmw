FME workspace 7_NYC_advancedDataStructure_addTexture_and_2Dto3D.fmw

Parameters:
- SourceDataset_JPEG = E:\New York City\Data\Texture\Roadbed_texture.jpg   # Source JPEG File(s)
- SourceDataset_CITYGML_13 = H:\Masterarbeit\Umsetzung\Datenexport Umsetzung\CityGML\Sidewalk_CityGML\Sidewalk_CityGML.gml   # Source CityGML File(s)
- SourceDataset_JPEG_13 = E:\New York City\Data\Texture\Plaza_Texture.jpg   # Source JPEG File(s)
- SourceDataset_JPEG_10 = E:\New York City\Data\Texture\Median_Painted_Texture.jpg   # Source JPEG File(s)
- SourceDataset_JPEG_11 = E:\New York City\Data\Texture\Curbs_Texture.jpg   # Source JPEG File(s)
- SourceDataset_JPEG_15 = E:\New York City\Data\Texture\Roadbed_texture.jpg   # Source JPEG File(s)
- SourceDataset_JPEG_12 = E:\New York City\Data\Texture\Median_Raised_Texture.JPG   # Source JPEG File(s)
- SourceDataset_JPEG_17 = E:\New York City\Data\Texture\Track_texture.jpg   # Source JPEG File(s)
- SourceDataset_JPEG_14 = E:\New York City\Data\Texture\Sidewalk_Texture.jpg   # Source JPEG File(s)
- SourceDataset_JPEG_16 = E:\New York City\Data\Texture\Grass_Texture.jpg   # Source JPEG File(s)
- DestDataset_CITYGML_8 = C:\Users\cbeil\Desktop\Streetspace\NYC_Flatiron_Streetspace_CityGML_LoD2.gml   # Destination CityGML Document
- SourceDataset_CITYGML = C:\Users\cbeil\Desktop\NYC_Flatiron_Streetspace_CityGML_LoD2.gml   # Source CityGML File(s)

Readers:
- JPEG_1: JPEG from $(SourceDataset_JPEG)
- CITYGML_1: CITYGML from $(SourceDataset_CITYGML_13)
- JPEG_2: JPEG from $(SourceDataset_JPEG_13)
- JPEG_3: JPEG from $(SourceDataset_JPEG_10)
- JPEG_4: JPEG from $(SourceDataset_JPEG_11)
- JPEG_5: JPEG from $(SourceDataset_JPEG_15)
- JPEG_6: JPEG from $(SourceDataset_JPEG_12)
- JPEG_7: JPEG from $(SourceDataset_JPEG_17)
- JPEG_8: JPEG from $(SourceDataset_JPEG_14)
- JPEG_9: JPEG from $(SourceDataset_JPEG_16)
- CITYGML_2: CITYGML from $(SourceDataset_CITYGML)

Writers:
- CITYGML_3: CITYGML to $(DestDataset_CITYGML_8)

TrafficArea (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer, bike_lane xml_buffer, construction_status xml_buffer, curve_flag xml_buffer, entrance_area_sqm xml_buffer, entrance_street_names xml_buffer, face_code xml_buffer,
      gml_name{} xml_buffer, intersecting_segements_count xml_buffer, intersecting_segmentIDs_conc xml_buffer, intersecting_street_names_conc xml_buffer, intersection_area_sqm xml_buffer, level_end_segment xml_buffer, level_start_segment xml_buffer, number_parking_lanes xml_buffer, number_total_lanes xml_buffer, number_travel_lanes xml_buffer, parking_lot xml_buffer, parking_lot_area_sqm xml_buffer, physical_id xml_buffer, plaza_area_sqm xml_buffer, plaza_height_inch xml_buffer, plaza_height_meter xml_buffer, radius_arc xml_buffer, sanitation_district_boundary_indicator xml_buffer, segment_count xml_buffer, segment_id xml_buffer, segment_type xml_buffer, sequence_number xml_buffer, sidewalk_area_sqm xml_buffer, sidewalk_height_inch xml_buffer, sidewalk_height_meter xml_buffer, slope_percent xml_buffer, snow_priority xml_buffer, special_address_place_name xml_buffer, special_address_place_name_2 xml_buffer, special_address_place_name_3 xml_buffer,
      special_address_place_name_4 xml_buffer, special_address_place_name_5 xml_buffer, special_address_place_name_6 xml_buffer, special_address_place_name_7 xml_buffer, special_address_type xml_buffer, special_address_type_2 xml_buffer, special_address_type_3 xml_buffer, special_address_type_4 xml_buffer, special_address_type_5 xml_buffer, special_address_type_6 xml_buffer, special_address_type_7 xml_buffer, street_area_2D_meter xml_buffer, street_code xml_buffer, street_length_2D_meter xml_buffer, street_length_3D_meter xml_buffer, street_pavement_rating_date xml_buffer, street_pavement_rating_num xml_buffer, street_pavement_rating_text xml_buffer, street_segment_width_meter xml_buffer, street_speed_limit_km_h xml_buffer, street_speed_limit_mph xml_buffer, street_width_2D_meter xml_buffer, traffic_area_2D_meter xml_buffer, traffic_direction xml_buffer, traffic_direction_source xml_buffer, gml_name{0} xml_buffer, gml_name{1} xml_buffer, gml_name{2} xml_buffer, gml_name{3} xml_buffer, gml_name{4} xml_buffer,
      gml_name{5} xml_buffer, gml_name{6} xml_buffer, gml_name{7} xml_buffer, gml_name{8} xml_buffer, gml_name{9} xml_buffer, gml_name{10} xml_buffer
    -> AttributeCreator_5
AttributeCreator_5
    ATTR_TABLE = SET_TO gml_geometry = MultiSurface
    -> TestFilter_3
TestFilter_3
    DEFAULT_VALUE = <UNFILTERED>
    TEST_LIST = BOOL_OP,OR,COMPOSITE_TEST,<Unused>,TEST_CLAUSE,"TEST @Value(citygml_class) = 350000",Roadbed,BOOL_OP,OR,COMPOSITE_TEST,<Unused>,TEST_CLAUSE,"TEST @Value(citygml_class) = 350010",Intersection,BOOL_OP,OR,COMPOSITE_TEST,<Unused>,TEST_CLAUSE,"TEST @Value(citygml_class) = 380030",Entrance,BOOL_OP,OR,COMPOSITE_TEST,<Unused>,TEST_CLAUSE,"TEST @Value(citygml_class) = 380000",Sidewalk,BOOL_OP,OR,COMPOSITE_TEST,<Unused>,TEST_CLAUSE,"TEST @Value(citygml_class) = 600000",Plaza,BOOL_OP,OR,COMPOSITE_TEST,<Unused>,TEST_CLAUSE,"TEST @Value(citygml_class) = 500000",Parking_Lot,BOOL_OP,OR,COMPOSITE_TEST,<Unused>,TEST_CLAUSE,"TEST @Value(citygml_class) = 380010",Track
    Roadbed -> Deaggregator_10
    Intersection -> Deaggregator_10
    Entrance -> Deaggregator_10
    Sidewalk -> Deaggregator_2
    Plaza -> Deaggregator
    Parking_Lot -> Deaggregator_11
    Track -> Deaggregator_5
    <UNFILTERED> -> Inspector
Inspector
AuxiliaryTrafficArea (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer, curb_area_sqm xml_buffer, curb_height_inch xml_buffer, curb_height_meter xml_buffer, median_area_sqm xml_buffer, median_height_inch xml_buffer, median_height_meter xml_buffer,
      median_volume_cubicmeter xml_buffer, segment_id xml_buffer, snow_priority xml_buffer
    -> AttributeCreator_4
AttributeCreator_4
    ATTR_TABLE = SET_TO gml_geometry = MultiSurface
    -> TestFilter_2
TestFilter_2
    DEFAULT_VALUE = <UNFILTERED>
    TEST_LIST = BOOL_OP,OR,COMPOSITE_TEST,<Unused>,TEST_CLAUSE,"TEST @Value(citygml_class) = 225000",Curbs,BOOL_OP,OR,COMPOSITE_TEST,<Unused>,TEST_CLAUSE,"TEST @Value(citygml_class) = 360010",Median_Painted,BOOL_OP,OR,COMPOSITE_TEST,<Unused>,TEST_CLAUSE,"TEST @Value(citygml_class) = 360020",Median_Raised,BOOL_OP,OR,COMPOSITE_TEST,<Unused>,TEST_CLAUSE,"TEST @Value(citygml_class) = 360050",Median_Grass
    Curbs -> Deaggregator_3
    Median_Painted -> AppearanceSetter_6 [GEOMETRY]
    Median_Raised -> Deaggregator_4
    Median_Grass -> Deaggregator_6
    <UNFILTERED> -> Inspector_2
Inspector_2
AuxiliaryTrafficArea (writer CITYGML_3)
    attributes: citygml_appearance{}.xlink_href xml_buffer, citygml_class xml_int16, citygml_class_codeSpace xml_buffer, citygml_creationDate xml_date, citygml_feature_role xml_buffer, citygml_feature_role_attr_name xml_buffer, citygml_feature_role_attr_val xml_buffer, citygml_function{} xml_int16, citygml_function{}.codeSpace xml_buffer, citygml_generalizes_to{}.xlink_href xml_buffer, citygml_level_of_detail{} xml_buffer, citygml_relative_to_terrain xml_char(33), citygml_relative_to_water xml_char(38), citygml_surface_material xml_buffer, citygml_surface_material_codeSpace xml_buffer, citygml_target_uri xml_buffer, citygml_terminationDate xml_date, citygml_usage{} xml_int16, citygml_usage{}.codeSpace xml_buffer, curb_area_sqm xml_decimal(20,10), curb_height_inch xml_decimal(20,10), curb_height_meter xml_decimal(20,10), externalReference{}.externalObject.name xml_xml, externalReference{}.externalObject.uri xml_xml, externalReference{}.informationSystem xml_xml, gml_description xml_buffer, gml_name xml_char(20), median_area_sqm xml_decimal(20,10), median_height_inch xml_decimal(20,10), median_height_meter xml_decimal(20,10),
      median_volume_cubicmeter xml_decimal(20,10), segment_id xml_int16, snow_priority xml_char(20)
TrafficArea (writer CITYGML_3)
    attributes: bike_lane xml_int16, citygml_appearance{}.xlink_href xml_buffer, citygml_class xml_int16, citygml_class_codeSpace xml_buffer, citygml_creationDate xml_date, citygml_feature_role xml_buffer, citygml_feature_role_attr_name xml_buffer, citygml_feature_role_attr_val xml_buffer, citygml_function{} xml_int16, citygml_function{}.codeSpace xml_buffer, citygml_generalizes_to{}.xlink_href xml_buffer, citygml_level_of_detail{} xml_int16, citygml_relative_to_terrain xml_char(33), citygml_relative_to_water xml_char(38), citygml_surface_material xml_int16, citygml_surface_material_codeSpace xml_buffer, citygml_target_uri xml_buffer, citygml_terminationDate xml_date, citygml_usage{} xml_int16, citygml_usage{}.codeSpace xml_buffer, construction_status xml_int16, curve_flag xml_buffer, entrance_area_sqm xml_decimal(20,10), entrance_street_names xml_char(20), externalReference{}.externalObject.name xml_xml, externalReference{}.externalObject.uri xml_xml, externalReference{}.informationSystem xml_xml, face_code xml_int16, gml_description xml_buffer, gml_name xml_char(20),
      gml_name{} xml_char(20), gml_name{0} xml_char(20), gml_name{1} xml_char(20), gml_name{2} xml_char(20), gml_name{3} xml_char(20), gml_name{4} xml_char(20), gml_name{5} xml_char(20), gml_name{6} xml_char(20), gml_name{7} xml_char(20), gml_name{8} xml_char(20), gml_name{9} xml_char(20), gml_name{10} xml_char(20), intersecting_segements_count xml_int16, intersecting_segmentIDs_conc xml_buffer, intersecting_street_names_conc xml_buffer, intersection_area_sqm xml_decimal(20,10), level_end_segment xml_int16, level_start_segment xml_int16, number_parking_lanes xml_int16, number_total_lanes xml_int16, number_travel_lanes xml_int16, parking_lot xml_buffer, parking_lot_area_sqm xml_decimal(20,10), physical_id xml_int16, plaza_area_sqm xml_decimal(20,10), plaza_height_inch xml_decimal(20,10), plaza_height_meter xml_decimal(20,10), radius_arc xml_decimal(20,10), sanitation_district_boundary_indicator xml_buffer, segment_count xml_int16,
      segment_id xml_int16, segment_type xml_char(20), sequence_number xml_int16, sidewalk_area_sqm xml_decimal(20,10), sidewalk_height_inch xml_decimal(20,10), sidewalk_height_meter xml_decimal(20,10), slope_percent xml_decimal(20,10), snow_priority xml_char(20), special_address_place_name xml_buffer, special_address_place_name_2 xml_buffer, special_address_place_name_3 xml_buffer, special_address_place_name_4 xml_buffer, special_address_place_name_5 xml_buffer, special_address_place_name_6 xml_buffer, special_address_place_name_7 xml_buffer, special_address_type xml_buffer, special_address_type_2 xml_buffer, special_address_type_3 xml_buffer, special_address_type_4 xml_buffer, special_address_type_5 xml_buffer, special_address_type_6 xml_buffer, special_address_type_7 xml_buffer, street_area_2D_meter xml_decimal(20,10), street_code xml_int16, street_length_2D_meter xml_decimal(20,10), street_length_3D_meter xml_decimal(20,10), street_pavement_rating_date xml_buffer, street_pavement_rating_num xml_int16, street_pavement_rating_text xml_char(20), street_segment_width_meter xml_decimal(20,10),
      street_speed_limit_km_h xml_decimal(20,10), street_speed_limit_mph xml_decimal(20,10), street_width_2D_meter xml_decimal(20,10), traffic_area_2D_meter xml_decimal(20,10), traffic_direction xml_char(20), traffic_direction_source xml_buffer

Bookmark: Roadbed / Intersection / Entrance Texture
Deaggregator_10
    MODE = Flatten One Level
    PART_NUMBER_FIELD = _part_number
    SPLIT_COMPOSITES = Yes
    EXPLODE_INSTANCES = No
    LIST_ATTR_MODE_LOOKUP = LEAN
    GEOM_NAME_FIELD = _geometry_name
    DEAGGREGATED -> AppearanceSetter [GEOMETRY]
JPEG (reader JPEG_1)
    -> AppearanceStyler
AppearanceStyler
    TEXTURE_U_SHEARING_FACTOR = 0.0
    TEXTURE_U_SCALING_FACTOR = 1.0
    DIFFUSE_COLOR = 1,1,1
    ALPHA = 1.0
    TEXTURE_U_OFFSET = 0.0
    TEXTURE_WRAP_DISPLAY = Repeat in U and V
    TEXTURE_CENTER_U = 0.0
    TEXTURE_ROTATION_ANGLE = 0.0
    TEXTURE_V_SCALING_FACTOR = 1.0
    TEXTURE_CENTER_V = 0.0
    TEXTURE_V_SHEARING_FACTOR = 0.0
    TEXTURE_V_OFFSET = 0.0
    -> AppearanceSetter [APPEARANCE]
AppearanceSetter
    TEXTURE_V_SCALE_FACTOR = 1.0
    TEXTURE_WRAP_DISPLAY = Repeat in U and V
    DEF_STORAGE = Create New Definitions
    TEXTURE_U_OFFSET2 = 0.0
    TEXTURE_U_SCALE_FACTOR = 1.0
    TEXTURE_U_SCALING_FACTOR = 0.1
    SET_ON_SIDE = Front Side
    USE_EXISTING_TEXTURE_COORDINATES = Yes
    TEXTURE_MAPPING_TYPE_CHOICE = From Top View
    TEXTURE_V_SCALING_FACTOR = 0.1
    GQUERY:
      for $geom in //geometry
      where $geom/count(parent::geometry) = 0
      return number($geom/@fme_id)
    TEXTURE_V_OFFSET2 = 0.0
    -> Aggregator_6
Aggregator_6
    AGGREGATE_TYPE = Homogeneous Collection (If Possible)
    SEP = ,
    ACCUM_ATTRS_NAME = Get Attributes From One Representative Feature
    MODE = Geometry - Assemble One Level
    ORDERED = No
    GROUP_BY = gml_id
    AGGREGATE -> AttributeRemover_5
AttributeRemover_5
    REMOVE_ATTRS = _geometry_name,_part_number
    -> CityGMLGeometrySetter
CityGMLGeometrySetter
    ROLE = trafficArea
    GEOM = lod2MultiSurface
    -> GeometryPropertySetter
GeometryPropertySetter
    SETTYPE_PARAM = Traits From Attributes
    REMOVE_ATTRIBUTE = No
    SRC_ATTRS = gml_geometry citygml_level_of_detail{0} citygml_feature_role citygml_lod_name
    OVERWRITE_CHOICE = Yes
    SET -> Roadbed
    SET -> TrafficArea (writer CITYGML_3)
Roadbed: Inspector

Bookmark: Sidewalk Texture
Deaggregator_2
    MODE = Flatten One Level
    PART_NUMBER_FIELD = _part_number
    SPLIT_COMPOSITES = No
    EXPLODE_INSTANCES = No
    LIST_ATTR_MODE_LOOKUP = LEAN
    GEOM_NAME_FIELD = _geometry_name
    DEAGGREGATED -> GeometryCoercer_7
GeometryCoercer_7
    KIND = fme_polygon
    GQUERY:
      for $geom in //geometry
      where $geom/count(parent::geometry) = 0
      return number($geom/@fme_id)
    COERCED -> Extruder_4
Extruder_4
    DIRECTION = Auto
    DISTANCE = 0.1524
    -> Deaggregator_12
Deaggregator_12
    MODE = Flatten One Level
    COPY_ATTR = Every Node
    PART_NUMBER_FIELD = _part_number
    ID_SELECTION = ID and Parent ID
    PARENT_ID_ATTR = _hierarchy_parent_id
    CHILD_ID_ATTR = _hierarchy_child_id_list
    ID_ATTR = _hierarchy_id
    SPLIT_COMPOSITES = No
    EXPLODE_INSTANCES = No
    LIST_ATTR_MODE_LOOKUP = LEAN
    GEOM_NAME_FIELD = _geometry_name
    DEAGGREGATED -> GeometryCoercer_8
GeometryCoercer_8
    KIND = fme_composite_surface
    GQUERY:
      for $geom in //geometry
      where $geom/count(parent::geometry) = 0
      return number($geom/@fme_id)
    COERCED -> AppearanceSetter_2 [GEOMETRY]
JPEG (reader JPEG_8)
    -> AppearanceStyler_2
AppearanceStyler_2
    TEXTURE_U_SHEARING_FACTOR = 0.0
    TEXTURE_U_SCALING_FACTOR = 1.0
    DIFFUSE_COLOR = 1,1,1
    ALPHA = 1.0
    TEXTURE_U_OFFSET = 0.0
    TEXTURE_WRAP_DISPLAY = Repeat in U and V
    TEXTURE_CENTER_U = 0.0
    TEXTURE_ROTATION_ANGLE = 0.0
    TEXTURE_V_SCALING_FACTOR = 1.0
    TEXTURE_CENTER_V = 0.0
    TEXTURE_V_SHEARING_FACTOR = 0.0
    TEXTURE_V_OFFSET = 0.0
    -> AppearanceSetter_2 [APPEARANCE]
AppearanceSetter_2
    TEXTURE_V_SCALE_FACTOR = 1.0
    TEXTURE_WRAP_DISPLAY = Repeat in U and V
    DEF_STORAGE = Create New Definitions
    TEXTURE_U_OFFSET2 = 0.0
    TEXTURE_U_SCALE_FACTOR = 1.0
    TEXTURE_U_SCALING_FACTOR = 0.1
    SET_ON_SIDE = Front Side
    USE_EXISTING_TEXTURE_COORDINATES = Yes
    TEXTURE_MAPPING_TYPE_CHOICE = From Top View
    TEXTURE_V_SCALING_FACTOR = 0.1
    GQUERY:
      for $geom in //geometry
      where $geom/count(parent::geometry) = 0
      return number($geom/@fme_id)
    TEXTURE_V_OFFSET2 = 0.0
    -> Aggregator_2
Aggregator_2
    AGGREGATE_TYPE = Homogeneous Collection (If Possible)
    SEP = ,
    ACCUM_ATTRS_NAME = Get Attributes From One Representative Feature
    MODE = Geometry - Assemble One Level
    ORDERED = No
    GROUP_BY = gml_id
    AGGREGATE -> AttributeRemover_4
AttributeRemover_4
    REMOVE_ATTRS = _hierarchy_child_id_list{0},_hierarchy_parent_id,_hierarchy_id,_geometry_name,_part_number
    -> CityGMLGeometrySetter_9
CityGMLGeometrySetter_9
    ROLE = trafficArea
    GEOM = lod2MultiSurface
    -> GeometryPropertySetter_9
GeometryPropertySetter_9
    SETTYPE_PARAM = Traits From Attributes
    REMOVE_ATTRIBUTE = No
    SRC_ATTRS = gml_geometry citygml_level_of_detail{0} citygml_feature_role citygml_lod_name
    OVERWRITE_CHOICE = Yes
    SET -> TrafficArea (writer CITYGML_3)
    SET -> Sidewalk
Sidewalk: Inspector

Bookmark: Parking_Lot Texture
Deaggregator_11
    MODE = Flatten One Level
    PART_NUMBER_FIELD = _part_number
    SPLIT_COMPOSITES = Yes
    EXPLODE_INSTANCES = No
    LIST_ATTR_MODE_LOOKUP = LEAN
    GEOM_NAME_FIELD = _geometry_name
    DEAGGREGATED -> AppearanceSetter_5 [GEOMETRY]
JPEG (reader JPEG_5)
    -> AppearanceStyler_5
AppearanceStyler_5
    TEXTURE_U_SHEARING_FACTOR = 0.0
    TEXTURE_U_SCALING_FACTOR = 1.0
    DIFFUSE_COLOR = 1,1,1
    ALPHA = 1.0
    TEXTURE_U_OFFSET = 0.0
    TEXTURE_WRAP_DISPLAY = Repeat in U and V
    TEXTURE_CENTER_U = 0.0
    TEXTURE_ROTATION_ANGLE = 0.0
    TEXTURE_V_SCALING_FACTOR = 1.0
    TEXTURE_CENTER_V = 0.0
    TEXTURE_V_SHEARING_FACTOR = 0.0
    TEXTURE_V_OFFSET = 0.0
    -> AppearanceSetter_5 [APPEARANCE]
AppearanceSetter_5
    TEXTURE_V_SCALE_FACTOR = 1.0
    TEXTURE_WRAP_DISPLAY = Repeat in U and V
    DEF_STORAGE = Create New Definitions
    TEXTURE_U_OFFSET2 = 0.0
    TEXTURE_U_SCALE_FACTOR = 1.0
    TEXTURE_U_SCALING_FACTOR = 0.2
    SET_ON_SIDE = Front Side
    USE_EXISTING_TEXTURE_COORDINATES = Yes
    TEXTURE_MAPPING_TYPE_CHOICE = From Top View
    TEXTURE_V_SCALING_FACTOR = 0.2
    GQUERY:
      for $geom in //geometry
      where $geom/count(parent::geometry) = 0
      return number($geom/@fme_id)
    TEXTURE_V_OFFSET2 = 0.0
    -> AttributeCreator_6
AttributeCreator_6
    ATTR_TABLE = SET_TO externalReference{0}.informationSystem = https://data.cityofnewyork.us/City-Government/Parking-Lot-Features/h7zy-iq3d/about
    -> Aggregator_7
Aggregator_7
    AGGREGATE_TYPE = Homogeneous Collection (If Possible)
    SEP = ,
    ACCUM_ATTRS_NAME = Get Attributes From One Representative Feature
    MODE = Geometry - Assemble One Level
    ORDERED = No
    GROUP_BY = gml_id
    AGGREGATE -> AttributeRemover_8
AttributeRemover_8
    REMOVE_ATTRS = _geometry_name,_part_number
    -> CityGMLGeometrySetter_8
CityGMLGeometrySetter_8
    ROLE = trafficArea
    GEOM = lod2MultiSurface
    -> GeometryPropertySetter_8
GeometryPropertySetter_8
    SETTYPE_PARAM = Traits From Attributes
    REMOVE_ATTRIBUTE = No
    SRC_ATTRS = gml_geometry citygml_level_of_detail{0} citygml_feature_role citygml_lod_name
    OVERWRITE_CHOICE = Yes
    SET -> TrafficArea (writer CITYGML_3)
    SET -> Parking_Lot
Parking_Lot: Inspector

Bookmark: Plaza Texture
Deaggregator
    MODE = Flatten One Level
    PART_NUMBER_FIELD = _part_number
    SPLIT_COMPOSITES = No
    EXPLODE_INSTANCES = No
    LIST_ATTR_MODE_LOOKUP = LEAN
    GEOM_NAME_FIELD = _geometry_name
    DEAGGREGATED -> GeometryCoercer
GeometryCoercer
    KIND = fme_polygon
    GQUERY:
      for $geom in //geometry
      where $geom/count(parent::geometry) = 0
      return number($geom/@fme_id)
    COERCED -> Extruder
Extruder
    DIRECTION = Auto
    DISTANCE = 0.1524
    -> Deaggregator_7
Deaggregator_7
    MODE = Flatten One Level
    COPY_ATTR = Every Node
    PART_NUMBER_FIELD = _part_number
    ID_SELECTION = ID and Parent ID
    PARENT_ID_ATTR = _hierarchy_parent_id
    CHILD_ID_ATTR = _hierarchy_child_id_list
    ID_ATTR = _hierarchy_id
    SPLIT_COMPOSITES = No
    EXPLODE_INSTANCES = No
    LIST_ATTR_MODE_LOOKUP = LEAN
    GEOM_NAME_FIELD = _geometry_name
    DEAGGREGATED -> GeometryCoercer_2
GeometryCoercer_2
    KIND = fme_composite_surface
    GQUERY:
      for $geom in //geometry
      where $geom/count(parent::geometry) = 0
      return number($geom/@fme_id)
    COERCED -> AppearanceSetter_3 [GEOMETRY]
JPEG (reader JPEG_2)
    -> AppearanceStyler_3
AppearanceStyler_3
    TEXTURE_U_SHEARING_FACTOR = 0.0
    TEXTURE_U_SCALING_FACTOR = 1.0
    DIFFUSE_COLOR = 1,1,1
    ALPHA = 1.0
    TEXTURE_U_OFFSET = 0.0
    TEXTURE_WRAP_DISPLAY = Repeat in U and V
    TEXTURE_CENTER_U = 0.0
    TEXTURE_ROTATION_ANGLE = 0.0
    TEXTURE_V_SCALING_FACTOR = 1.0
    TEXTURE_CENTER_V = 0.0
    TEXTURE_V_SHEARING_FACTOR = 0.0
    TEXTURE_V_OFFSET = 0.0
    -> AppearanceSetter_3 [APPEARANCE]
AppearanceSetter_3
    TEXTURE_V_SCALE_FACTOR = 1.0
    TEXTURE_WRAP_DISPLAY = Repeat in U and V
    DEF_STORAGE = Create New Definitions
    TEXTURE_U_OFFSET2 = 0.0
    TEXTURE_U_SCALE_FACTOR = 1.0
    TEXTURE_U_SCALING_FACTOR = 0.1
    SET_ON_SIDE = Front Side
    USE_EXISTING_TEXTURE_COORDINATES = No
    TEXTURE_MAPPING_TYPE_CHOICE = From Top View
    TEXTURE_V_SCALING_FACTOR = 0.1
    GQUERY:
      for $geom in //geometry
      where $geom/count(parent::geometry) = 0
      return number($geom/@fme_id)
    TEXTURE_V_OFFSET2 = 0.0
    -> Aggregator
Aggregator
    AGGREGATE_TYPE = Homogeneous Collection (If Possible)
    SEP = ,
    ACCUM_ATTRS_NAME = Get Attributes From One Representative Feature
    MODE = Geometry - Assemble One Level
    ORDERED = No
    GROUP_BY = gml_id
    AGGREGATE -> AttributeRemover
AttributeRemover
    REMOVE_ATTRS = _hierarchy_child_id_list{0},_hierarchy_parent_id,_hierarchy_id,_geometry_name,_part_number
    -> CityGMLGeometrySetter_4
CityGMLGeometrySetter_4
    ROLE = trafficArea
    GEOM = lod2MultiSurface
    -> GeometryPropertySetter_4
GeometryPropertySetter_4
    SETTYPE_PARAM = Traits From Attributes
    REMOVE_ATTRIBUTE = No
    SRC_ATTRS = gml_geometry citygml_level_of_detail{0} citygml_feature_role citygml_lod_name
    OVERWRITE_CHOICE = Yes
    SET -> TrafficArea (writer CITYGML_3)
    SET -> Plaza
Plaza: Inspector

Bookmark: Track Texture
Deaggregator_5
    MODE = Flatten One Level
    PART_NUMBER_FIELD = _part_number
    SPLIT_COMPOSITES = Yes
    EXPLODE_INSTANCES = No
    LIST_ATTR_MODE_LOOKUP = LEAN
    GEOM_NAME_FIELD = _geometry_name
    DEAGGREGATED -> AppearanceSetter_8 [GEOMETRY]
JPEG (reader JPEG_7)
    -> AppearanceStyler_8
AppearanceStyler_8
    TEXTURE_U_SHEARING_FACTOR = 0.0
    TEXTURE_U_SCALING_FACTOR = 1.0
    DIFFUSE_COLOR = 1,1,1
    ALPHA = 1.0
    TEXTURE_U_OFFSET = 0.0
    TEXTURE_WRAP_DISPLAY = Repeat in U and V
    TEXTURE_CENTER_U = 0.0
    TEXTURE_ROTATION_ANGLE = 0.0
    TEXTURE_V_SCALING_FACTOR = 1.0
    TEXTURE_CENTER_V = 0.0
    TEXTURE_V_SHEARING_FACTOR = 0.0
    TEXTURE_V_OFFSET = 0.0
    -> AppearanceSetter_8 [APPEARANCE]
AppearanceSetter_8
    TEXTURE_V_SCALE_FACTOR = 1.0
    TEXTURE_WRAP_DISPLAY = Repeat in U and V
    DEF_STORAGE = Create New Definitions
    TEXTURE_U_OFFSET2 = 0.0
    TEXTURE_U_SCALE_FACTOR = 1.0
    TEXTURE_U_SCALING_FACTOR = 0.05
    SET_ON_SIDE = Front Side
    USE_EXISTING_TEXTURE_COORDINATES = Yes
    TEXTURE_MAPPING_TYPE_CHOICE = From Top View
    TEXTURE_V_SCALING_FACTOR = 0.05
    GQUERY:
      for $geom in //geometry
      where $geom/count(parent::geometry) = 0
      return number($geom/@fme_id)
    TEXTURE_V_OFFSET2 = 0.0
    -> Aggregator_5
Aggregator_5
    AGGREGATE_TYPE = Homogeneous Collection (If Possible)
    SEP = ,
    ACCUM_ATTRS_NAME = Get Attributes From One Representative Feature
    MODE = Geometry - Assemble One Level
    ORDERED = No
    GROUP_BY = gml_id
    AGGREGATE -> AttributeRemover_6
AttributeRemover_6
    REMOVE_ATTRS = _geometry_name,_part_number
    -> CityGMLGeometrySetter_3
CityGMLGeometrySetter_3
    ROLE = trafficArea
    GEOM = lod2MultiSurface
    -> GeometryPropertySetter_3
GeometryPropertySetter_3
    SETTYPE_PARAM = Traits From Attributes
    REMOVE_ATTRIBUTE = No
    SRC_ATTRS = gml_geometry citygml_level_of_detail{0} citygml_feature_role citygml_lod_name
    OVERWRITE_CHOICE = Yes
    SET -> Track
    SET -> TrafficArea (writer CITYGML_3)
Track: Inspector

Bookmark: Curbs Texture
Deaggregator_3
    MODE = Flatten One Level
    COPY_ATTR = Every Node
    PART_NUMBER_FIELD = _part_number
    ID_SELECTION = ID and Parent ID
    PARENT_ID_ATTR = _hierarchy_parent_id
    CHILD_ID_ATTR = _hierarchy_child_id_list
    ID_ATTR = _hierarchy_id
    SPLIT_COMPOSITES = No
    EXPLODE_INSTANCES = No
    LIST_ATTR_MODE_LOOKUP = LEAN
    GEOM_NAME_FIELD = _geometry_name
    DEAGGREGATED -> GeometryCoercer_5
GeometryCoercer_5
    KIND = fme_polygon
    GQUERY:
      for $geom in //geometry
      where $geom/count(parent::geometry) = 0
      return number($geom/@fme_id)
    COERCED -> Extruder_3
Extruder_3
    DIRECTION = Auto
    DISTANCE = 0.1524
    -> Deaggregator_9
Deaggregator_9
    MODE = Flatten One Level
    COPY_ATTR = Every Node
    PART_NUMBER_FIELD = _part_number
    ID_SELECTION = ID and Parent ID
    PARENT_ID_ATTR = _hierarchy_parent_id
    CHILD_ID_ATTR = _hierarchy_child_id_list
    ID_ATTR = _hierarchy_id
    SPLIT_COMPOSITES = No
    EXPLODE_INSTANCES = No
    LIST_ATTR_MODE_LOOKUP = LEAN
    GEOM_NAME_FIELD = _geometry_name
    DEAGGREGATED -> GeometryCoercer_6
GeometryCoercer_6
    KIND = fme_composite_surface
    GQUERY:
      for $geom in //geometry
      where $geom/count(parent::geometry) = 0
      return number($geom/@fme_id)
    COERCED -> AppearanceSetter_4 [GEOMETRY]
JPEG (reader JPEG_4)
    -> AppearanceStyler_4
AppearanceStyler_4
    TEXTURE_U_SHEARING_FACTOR = 0.0
    TEXTURE_U_SCALING_FACTOR = 1.0
    DIFFUSE_COLOR = 1,1,1
    ALPHA = 1.0
    TEXTURE_U_OFFSET = 0.0
    TEXTURE_WRAP_DISPLAY = Repeat in U and V
    TEXTURE_CENTER_U = 0.0
    TEXTURE_ROTATION_ANGLE = 0.0
    TEXTURE_V_SCALING_FACTOR = 1.0
    TEXTURE_CENTER_V = 0.0
    TEXTURE_V_SHEARING_FACTOR = 0.0
    TEXTURE_V_OFFSET = 0.0
    -> AppearanceSetter_4 [APPEARANCE]
AppearanceSetter_4
    TEXTURE_V_SCALE_FACTOR = 1.0
    TEXTURE_WRAP_DISPLAY = Repeat in U and V
    DEF_STORAGE = Create New Definitions
    TEXTURE_U_OFFSET2 = 0.0
    TEXTURE_U_SCALE_FACTOR = 1.0
    TEXTURE_U_SCALING_FACTOR = 0.2
    SET_ON_SIDE = Front Side
    USE_EXISTING_TEXTURE_COORDINATES = Yes
    TEXTURE_MAPPING_TYPE_CHOICE = From Top View
    TEXTURE_V_SCALING_FACTOR = 0.2
    GQUERY:
      for $geom in //geometry
      where $geom/count(parent::geometry) = 0
      return number($geom/@fme_id)
    TEXTURE_V_OFFSET2 = 0.0
    -> Aggregator_3
Aggregator_3
    AGGREGATE_TYPE = Homogeneous Collection (If Possible)
    SEP = ,
    ACCUM_ATTRS_NAME = Get Attributes From One Representative Feature
    MODE = Geometry - Assemble One Level
    ORDERED = No
    GROUP_BY = gml_id
    AGGREGATE -> AttributeRemover_3
AttributeRemover_3
    REMOVE_ATTRS = _hierarchy_child_id_list{0},_hierarchy_parent_id,_hierarchy_id,_geometry_name,_part_number
    -> CityGMLGeometrySetter_2
CityGMLGeometrySetter_2
    ROLE = auxiliaryTrafficArea
    GEOM = lod2MultiSurface
    -> GeometryPropertySetter_2
GeometryPropertySetter_2
    SETTYPE_PARAM = Traits From Attributes
    REMOVE_ATTRIBUTE = No
    SRC_ATTRS = gml_geometry citygml_level_of_detail{0} citygml_feature_role citygml_lod_name
    OVERWRITE_CHOICE = Yes
    SET -> AuxiliaryTrafficArea (writer CITYGML_3)
    SET -> Curbs
Curbs: Inspector

Bookmark: Raised
Deaggregator_4
    MODE = Flatten One Level
    PART_NUMBER_FIELD = _part_number
    SPLIT_COMPOSITES = No
    EXPLODE_INSTANCES = No
    LIST_ATTR_MODE_LOOKUP = LEAN
    GEOM_NAME_FIELD = _geometry_name
    DEAGGREGATED -> GeometryCoercer_3
GeometryCoercer_3
    KIND = fme_polygon
    GQUERY:
      for $geom in //geometry
      where $geom/count(parent::geometry) = 0
      return number($geom/@fme_id)
    COERCED -> Extruder_2
Extruder_2
    DIRECTION = Auto
    DISTANCE = 0.3048
    -> Deaggregator_8
Deaggregator_8
    MODE = Flatten One Level
    COPY_ATTR = Every Node
    PART_NUMBER_FIELD = _part_number
    ID_SELECTION = ID and Parent ID
    PARENT_ID_ATTR = _hierarchy_parent_id
    CHILD_ID_ATTR = _hierarchy_child_id_list
    ID_ATTR = _hierarchy_id
    SPLIT_COMPOSITES = No
    EXPLODE_INSTANCES = No
    LIST_ATTR_MODE_LOOKUP = LEAN
    GEOM_NAME_FIELD = _geometry_name
    DEAGGREGATED -> GeometryCoercer_4
GeometryCoercer_4
    KIND = fme_composite_surface
    GQUERY:
      for $geom in //geometry
      where $geom/count(parent::geometry) = 0
      return number($geom/@fme_id)
    COERCED -> AppearanceSetter_7 [GEOMETRY]
JPEG (reader JPEG_6)
    -> AppearanceStyler_7
AppearanceStyler_7
    TEXTURE_U_SHEARING_FACTOR = 0.0
    TEXTURE_U_SCALING_FACTOR = 1.0
    DIFFUSE_COLOR = 1,1,1
    ALPHA = 1.0
    TEXTURE_U_OFFSET = 0.0
    TEXTURE_WRAP_DISPLAY = Repeat in U and V
    TEXTURE_CENTER_U = 0.0
    TEXTURE_ROTATION_ANGLE = 0.0
    TEXTURE_V_SCALING_FACTOR = 1.0
    TEXTURE_CENTER_V = 0.0
    TEXTURE_V_SHEARING_FACTOR = 0.0
    TEXTURE_V_OFFSET = 0.0
    -> AppearanceSetter_7 [APPEARANCE]
AppearanceSetter_7
    TEXTURE_V_SCALE_FACTOR = 1.0
    TEXTURE_WRAP_DISPLAY = Repeat in U and V
    DEF_STORAGE = Create New Definitions
    TEXTURE_U_OFFSET2 = 0.0
    TEXTURE_U_SCALE_FACTOR = 1.0
    TEXTURE_U_SCALING_FACTOR = 0.2
    SET_ON_SIDE = Front Side
    USE_EXISTING_TEXTURE_COORDINATES = Yes
    TEXTURE_MAPPING_TYPE_CHOICE = From Top View
    TEXTURE_V_SCALING_FACTOR = 0.2
    GQUERY:
      for $geom in //geometry
      where $geom/count(parent::geometry) = 0
      return number($geom/@fme_id)
    TEXTURE_V_OFFSET2 = 0.0
    -> Aggregator_4
Aggregator_4
    AGGREGATE_TYPE = Homogeneous Collection (If Possible)
    SEP = ,
    ACCUM_ATTRS_NAME = Get Attributes From One Representative Feature
    MODE = Geometry - Assemble One Level
    ORDERED = No
    GROUP_BY = gml_id
    AGGREGATE -> AttributeRemover_2
AttributeRemover_2
    REMOVE_ATTRS = _part_number,_ymin,_geometry_name,_ymax,_zmin,_xmin,_zmax,_xmax
    -> CityGMLGeometrySetter_6
CityGMLGeometrySetter_6
    ROLE = auxiliaryTrafficArea
    GEOM = lod2MultiSurface
    -> GeometryPropertySetter_6
GeometryPropertySetter_6
    SETTYPE_PARAM = Traits From Attributes
    REMOVE_ATTRIBUTE = No
    SRC_ATTRS = gml_geometry citygml_level_of_detail{0} citygml_feature_role citygml_lod_name
    OVERWRITE_CHOICE = Yes
    SET -> AuxiliaryTrafficArea (writer CITYGML_3)
    SET -> Median_Raised
Median_Raised: Inspector

Bookmark: Grass
Deaggregator_6
    MODE = Flatten One Level
    PART_NUMBER_FIELD = _part_number
    SPLIT_COMPOSITES = No
    EXPLODE_INSTANCES = No
    LIST_ATTR_MODE_LOOKUP = LEAN
    GEOM_NAME_FIELD = _geometry_name
    DEAGGREGATED -> AppearanceSetter_9 [GEOMETRY]
JPEG (reader JPEG_9)
    -> AppearanceStyler_9
AppearanceStyler_9
    TEXTURE_U_SHEARING_FACTOR = 0.0
    TEXTURE_U_SCALING_FACTOR = 1.0
    DIFFUSE_COLOR = 1,1,1
    ALPHA = 1.0
    TEXTURE_U_OFFSET = 0.0
    TEXTURE_WRAP_DISPLAY = Repeat in U and V
    TEXTURE_CENTER_U = 0.0
    TEXTURE_ROTATION_ANGLE = 0.0
    TEXTURE_V_SCALING_FACTOR = 1.0
    TEXTURE_CENTER_V = 0.0
    TEXTURE_V_SHEARING_FACTOR = 0.0
    TEXTURE_V_OFFSET = 0.0
    -> AppearanceSetter_9 [APPEARANCE]
AppearanceSetter_9
    TEXTURE_V_SCALE_FACTOR = 1.0
    TEXTURE_WRAP_DISPLAY = Repeat in U and V
    DEF_STORAGE = Create New Definitions
    TEXTURE_U_OFFSET2 = 0.0
    TEXTURE_U_SCALE_FACTOR = 1.0
    TEXTURE_U_SCALING_FACTOR = 0.2
    SET_ON_SIDE = Front Side
    USE_EXISTING_TEXTURE_COORDINATES = Yes
    TEXTURE_MAPPING_TYPE_CHOICE = From Top View
    TEXTURE_V_SCALING_FACTOR = 0.2
    GQUERY:
      for $geom in //geometry
      where $geom/count(parent::geometry) = 0
      return number($geom/@fme_id)
    TEXTURE_V_OFFSET2 = 0.0
    -> Aggregator_8
Aggregator_8
    AGGREGATE_TYPE = Homogeneous Collection (If Possible)
    SEP = ,
    ACCUM_ATTRS_NAME = Get Attributes From One Representative Feature
    MODE = Geometry - Assemble One Level
    ORDERED = No
    GROUP_BY = gml_id
    AGGREGATE -> AttributeRemover_9
AttributeRemover_9
    REMOVE_ATTRS = _geometry_name,_part_number
    -> CityGMLGeometrySetter_7
CityGMLGeometrySetter_7
    ROLE = auxiliaryTrafficArea
    GEOM = lod2MultiSurface
    -> GeometryPropertySetter_7
GeometryPropertySetter_7
    SETTYPE_PARAM = Traits From Attributes
    REMOVE_ATTRIBUTE = No
    SRC_ATTRS = gml_geometry citygml_level_of_detail{0} citygml_feature_role citygml_lod_name
    OVERWRITE_CHOICE = Yes
    SET -> AuxiliaryTrafficArea (writer CITYGML_3)
    SET -> Median_Grass
Median_Grass: Inspector

Bookmark: CityModel
Creator
    NUM = 1
    GEOMTYPE = Geometry Object
    CREATED -> AttributeCreator_9
AttributeCreator_9
    ATTR_TABLE:
      SET_TO gml_id = NYC
      SET_TO gml_name = NYC Flatiron Streetspace Model CityGML
    -> CityModel (writer CITYGML_3)
CityModel (writer CITYGML_3)
    attributes: gml_name xml_buffer, _creation_instance xml_char(200)
Road (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, gml_name{} xml_buffer
    -> AttributeCreator
AttributeCreator
    ATTR_TABLE = SET_TO gml_parent_id = NYC
    -> Road (writer CITYGML_3)
Road (writer CITYGML_3)
    attributes: citygml_appearance{}.xlink_href xml_buffer, citygml_auxiliary_traffic_area{}.xlink_href xml_buffer, citygml_class xml_buffer, citygml_class_codeSpace xml_buffer, citygml_creationDate xml_date, citygml_feature_role xml_buffer, citygml_feature_role_attr_name xml_buffer, citygml_feature_role_attr_val xml_buffer, citygml_function{} xml_buffer, citygml_function{}.codeSpace xml_buffer, citygml_generalizes_to{}.xlink_href xml_buffer, citygml_level_of_detail{} xml_buffer, citygml_relative_to_terrain xml_char(33), citygml_relative_to_water xml_char(38), citygml_target_uri xml_buffer, citygml_terminationDate xml_date, citygml_traffic_area{}.xlink_href xml_buffer, citygml_usage{} xml_buffer, citygml_usage{}.codeSpace xml_buffer, externalReference{}.externalObject.name xml_xml, externalReference{}.externalObject.uri xml_xml, externalReference{}.informationSystem xml_xml, gml_description xml_buffer, gml_name xml_buffer, gml_name{} xml_buffer
Track (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer
    -> AttributeCreator_2
AttributeCreator_2
    ATTR_TABLE = SET_TO gml_parent_id = NYC
    -> Track (writer CITYGML_3)
Track (writer CITYGML_3)
    attributes: citygml_appearance{}.xlink_href xml_buffer, citygml_auxiliary_traffic_area{}.xlink_href xml_buffer, citygml_class xml_buffer, citygml_class_codeSpace xml_buffer, citygml_creationDate xml_date, citygml_feature_role xml_buffer, citygml_feature_role_attr_name xml_buffer, citygml_feature_role_attr_val xml_buffer, citygml_function{} xml_buffer, citygml_function{}.codeSpace xml_buffer, citygml_generalizes_to{}.xlink_href xml_buffer, citygml_level_of_detail{} xml_buffer, citygml_relative_to_terrain xml_char(33), citygml_relative_to_water xml_char(38), citygml_target_uri xml_buffer, citygml_terminationDate xml_date, citygml_traffic_area{}.xlink_href xml_buffer, citygml_usage{} xml_buffer, citygml_usage{}.codeSpace xml_buffer, externalReference{}.externalObject.name xml_xml, externalReference{}.externalObject.uri xml_xml, externalReference{}.informationSystem xml_xml, gml_description xml_buffer, gml_name xml_buffer
Square (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer
    -> AttributeCreator_3
AttributeCreator_3
    ATTR_TABLE = SET_TO gml_parent_id = NYC
    -> Square (writer CITYGML_3)
Square (writer CITYGML_3)
    attributes: citygml_appearance{}.xlink_href xml_buffer, citygml_auxiliary_traffic_area{}.xlink_href xml_buffer, citygml_class xml_buffer, citygml_class_codeSpace xml_buffer, citygml_creationDate xml_date, citygml_feature_role xml_buffer, citygml_feature_role_attr_name xml_buffer, citygml_feature_role_attr_val xml_buffer, citygml_function{} xml_buffer, citygml_function{}.codeSpace xml_buffer, citygml_generalizes_to{}.xlink_href xml_buffer, citygml_level_of_detail{} xml_buffer, citygml_relative_to_terrain xml_char(33), citygml_relative_to_water xml_char(38), citygml_target_uri xml_buffer, citygml_terminationDate xml_date, citygml_traffic_area{}.xlink_href xml_buffer, citygml_usage{} xml_buffer, citygml_usage{}.codeSpace xml_buffer, externalReference{}.externalObject.name xml_xml, externalReference{}.externalObject.uri xml_xml, externalReference{}.informationSystem xml_xml, gml_description xml_buffer, gml_name xml_buffer

Bookmark: Painted
JPEG (reader JPEG_3)
    -> AppearanceStyler_6
AppearanceStyler_6
    TEXTURE_U_SHEARING_FACTOR = 0.0
    TEXTURE_U_SCALING_FACTOR = 1.0
    DIFFUSE_COLOR = 1,1,1
    ALPHA = 1.0
    TEXTURE_U_OFFSET = 0.0
    TEXTURE_WRAP_DISPLAY = Repeat in U and V
    TEXTURE_CENTER_U = 0.0
    TEXTURE_ROTATION_ANGLE = 0.0
    TEXTURE_V_SCALING_FACTOR = 1.0
    TEXTURE_CENTER_V = 0.0
    TEXTURE_V_SHEARING_FACTOR = 0.0
    TEXTURE_V_OFFSET = 0.0
    -> AppearanceSetter_6 [APPEARANCE]
AppearanceSetter_6
    TEXTURE_V_SCALE_FACTOR = 1.0
    TEXTURE_WRAP_DISPLAY = Repeat in U and V
    DEF_STORAGE = Create New Definitions
    TEXTURE_U_OFFSET2 = 0.0
    TEXTURE_U_SCALE_FACTOR = 1.0
    TEXTURE_U_SCALING_FACTOR = 0.2
    SET_ON_SIDE = Front Side
    USE_EXISTING_TEXTURE_COORDINATES = Yes
    TEXTURE_MAPPING_TYPE_CHOICE = From Top View
    TEXTURE_V_SCALING_FACTOR = 0.2
    GQUERY:
      for $geom in //geometry
      where $geom/count(parent::geometry) = 0
      return number($geom/@fme_id)
    TEXTURE_V_OFFSET2 = 0.0
    -> AttributeRemover_7
AttributeRemover_7
    -> CityGMLGeometrySetter_5
CityGMLGeometrySetter_5
    ROLE = auxiliaryTrafficArea
    GEOM = lod2MultiSurface
    -> GeometryPropertySetter_5
GeometryPropertySetter_5
    SETTYPE_PARAM = Traits From Attributes
    REMOVE_ATTRIBUTE = No
    SRC_ATTRS = gml_geometry citygml_level_of_detail{0} citygml_feature_role citygml_lod_name
    OVERWRITE_CHOICE = Yes
    SET -> AuxiliaryTrafficArea (writer CITYGML_3)
    SET -> Median_Painted
Median_Painted: Inspector

FME custom transformer CityGMLGeometrySetter
This transformer provides a convenient way to set both the CityGML LOD Name and role from a preset list of options.
Input Ports
    Input
    Features to tag with City LOD name and feature role 
    Output Ports
    Output
    Features tagged with City LOD name and feature role 
    Parameters
    CityGML Lod Name
    Select the desired CityGML Lod name
    Feature Role
    Select the desired feature role

Parameters:
- GEOM =   # CityGML Lod Name
- ROLE =   # Feature Role

INPUT (input)
    -> AttributeCreator
Note: Set LOD name / and citygml role
AttributeCreator
    ATTR_TABLE:
      SET_TO citygml_lod_name = $(GEOM)
      SET_TO citygml_feature_role = $(ROLE)
    -> GeometryPropertySetter
Note: Convert LOD to geometry trait
GeometryPropertySetter
    SETTYPE_PARAM = Traits From Attributes
    REMOVE_ATTRIBUTE = No
    SRC_ATTRS = citygml_lod_name
    OVERWRITE_CHOICE = Yes
    SET -> OUTPUT (output)
OUTPUT (output)
