FME workspace 1_NYC_CenterlinesMergeAttributes.fmw

Parameters:
- SourceDataset_CITYGML = H:\Masterarbeit\Umsetzung\Datengrundlage\NYC_Flatiron_Buildings_Streets_Lots_20150907.gml   # Source CityGML File(s)
- SourceDataset_ESRISHAPE_12 = H:\Masterarbeit\Umsetzung\Datengrundlage\Street Pavement Rating\geo_export_a8b3f54a-5887-4bab-8943-c95b8125db62.shp   # Source Esri Shapefile(s)
- SourceDataset_ESRISHAPE = H:\Masterarbeit\Umsetzung\Datengrundlage\speed_limit_shapefile\speed_limit_shapefile_WGS\speed_limit_WGS.shp   # Source Esri Shapefile(s)
- SourceDataset_ESRISHAPE_6 = H:\Masterarbeit\Umsetzung\Datengrundlage\LION16\Centerline_LION16_Output.shp   # Source Esri Shapefile(s)
- DestDataset_CITYGML = H:\Masterarbeit\Umsetzung\Output\LoD0\Streetspace_LoD0.gml   # Destination CityGML Document
- SourceDataset_CITYGML_3 = H:\Masterarbeit\Umsetzung\Datengrundlage\Gesamtgebiet\NYC_Streets_CityGML_20150907\NYC_Streets_CityGML_20150907.gml   # Source CityGML File(s)

Readers:
- CITYGML_1: CITYGML from $(SourceDataset_CITYGML)
- ESRISHAPE_1: ESRISHAPE from $(SourceDataset_ESRISHAPE_12)
- ESRISHAPE_2: ESRISHAPE from $(SourceDataset_ESRISHAPE)
- CITYGML_2: CITYGML from $(SourceDataset_CITYGML_3)
- ESRISHAPE_3: ESRISHAPE from $(SourceDataset_ESRISHAPE_6)

Writers:
- CITYGML_3: CITYGML to $(DestDataset_CITYGML)

Note: In this Workspace information on streets form different source are integrated into one CityGML compliant lod0Network dataset.
Note: Set CityGML feature role and geometry attribute

Bookmark: CityModel
Creator
    GEOMTYPE = Geometry Object
    NUM = 1
    CREATED -> AttributeCreator_6
AttributeCreator_6
    ATTR_TABLE:
      SET_TO gml_id = NYC
      SET_TO gml_name = New York City Model
    -> CityModel (writer CITYGML_3)
CityModel (writer CITYGML_3) [off]
    attributes: gml_name xml_buffer, _creation_instance xml_char(200)

Bookmark: Pavement Ratings
geo_export_a8b3f54a-5887-4bab-8943-c95b8125db62 (reader ESRISHAPE_1) [off]
    attributes: segment_id number(33,31), rating_fy_ number(33,31), date_ratin date, time_ratin char(254), rating_b number(33,31), rating_wor char(254), usage_clas char(254), width number(33,31), length number(33,31), shape_len number(33,31)
    -> AttributeCreator

Bookmark: Pavement Rating
Note: Rename relevant attributes and remove irrelevant attributes
AttributeCreator
    ATTR_TABLE:
      SET_TO street_segment_width_meter = @Evaluate(@Value(width)/3.28084)
      SET_TO externalReference{1}.informationSystem  = https://data.cityofnewyork.us/Transportation/Street-Pavement-Rating/2cav-chmn/data
      SET_TO externalReference{1}.externalObject.name = @Value(segment_id)
    -> AttributeRenamer_3
AttributeRenamer_3
    ATTR_TABLE:
      RENAME_SET_DEFAULT date_ratin > street_pavement_rating_date
      RENAME_SET_DEFAULT rating_b > street_pavement_rating_num
      RENAME_SET_DEFAULT rating_wor > street_pavement_rating_text
    -> AttributeRemover_2
AttributeRemover_2
    REMOVE_ATTRS = length,rating_fy_,shape_len,width,time_ratin,usage_clas
    -> AttributeKeeper_4
AttributeKeeper_4
    KEEP_ATTRS = externalReference{1}.informationSystem ,externalReference{3}.externalObject.name,externalReference{5}.informationSystem ,externalReference{3}.informationSystem ,externalReference{4}.externalObject.name,externalReference{4}.informationSystem ,externalReference{2}.externalObject.name,externalReference{5}.externalObject.name,street_pavement_rating_num,externalReference{0}.externalObject.name,street_segment_width_meter,externalReference{1}.externalObject.name,externalReference{0}.informationSystem ,street_pavement_rating_date,externalReference{2}.informationSystem ,segment_id,street_pavement_rating_text
    -> FeatureMerger [SUPPLIER]

Bookmark: Test area
Road (reader CITYGML_1) [off]
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_function{} xml_buffer, citygml_usage{} xml_buffer, citygml_traffic_area{}.xlink_href xml_buffer, citygml_auxiliary_traffic_area{}.xlink_href xml_buffer, citygml_level_of_detail{} xml_buffer, bike_lane xml_buffer, citygml_class xml_buffer, construction_status xml_buffer, curve_flag xml_buffer, face_code xml_buffer, level_end_segment xml_buffer, level_start_segment xml_buffer, node_id_from xml_buffer, node_id_to xml_buffer, physical_id xml_buffer, radius_arc xml_buffer, sanitation_district_boundary_indicator xml_buffer,
      segment_count xml_buffer, segment_id xml_buffer, segment_type xml_buffer, sequence_number xml_buffer, snow_priority xml_buffer, special_address_place_name xml_buffer, special_address_place_name_2 xml_buffer, special_address_place_name_3 xml_buffer, special_address_place_name_4 xml_buffer, special_address_place_name_5 xml_buffer, special_address_type xml_buffer, special_address_type_2 xml_buffer, special_address_type_3 xml_buffer, special_address_type_4 xml_buffer, special_address_type_5 xml_buffer, street_area_2D_sq_m xml_buffer, street_code xml_buffer, street_length_2D_meter xml_buffer, street_width_meter xml_buffer, traffic_direction xml_buffer, traffic_direction_source xml_buffer
    -> Intersector_2

Bookmark: Total area
Road (reader CITYGML_2) [off]
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, GE_LoD1_zOffset xml_buffer, bike_lane xml_buffer, construction_status xml_buffer, curve_flag xml_buffer, face_code xml_buffer, level_end_segment xml_buffer, level_start_segment xml_buffer,
      merge2_citygml_class xml_buffer, merge2_citygml_function xml_buffer, merge2_construction_status xml_buffer, merge2_curve_flag xml_buffer, merge2_face_code xml_buffer, merge2_gml_name xml_buffer, merge2_level_end_segment xml_buffer, merge2_level_start_segment xml_buffer, merge2_non_pedestrian xml_buffer, merge2_physical_id xml_buffer, merge2_radius_arc xml_buffer, merge2_segment_count xml_buffer, merge2_segment_id xml_buffer, merge2_segment_type xml_buffer, merge2_sequence_number xml_buffer, merge2_snow_priority xml_buffer, merge2_street_code xml_buffer, merge2_traffic_direction xml_buffer, merge2_traffic_direction_source xml_buffer, merge3_citygml_class xml_buffer, merge3_citygml_function xml_buffer, merge3_construction_status xml_buffer, merge3_curve_flag xml_buffer, merge3_face_code xml_buffer, merge3_gml_name xml_buffer, merge3_level_end_segment xml_buffer, merge3_level_start_segment xml_buffer, merge3_non_pedestrian xml_buffer, merge3_physical_id xml_buffer, merge3_radius_arc xml_buffer,
      merge3_segment_count xml_buffer, merge3_segment_id xml_buffer, merge3_segment_type xml_buffer, merge3_sequence_number xml_buffer, merge3_snow_priority xml_buffer, merge3_street_code xml_buffer, merge3_traffic_direction xml_buffer, merge3_traffic_direction_source xml_buffer, merge4_citygml_class xml_buffer, merge4_citygml_function xml_buffer, merge4_construction_status xml_buffer, merge4_face_code xml_buffer, merge4_gml_name xml_buffer, merge4_level_end_segment xml_buffer, merge4_level_start_segment xml_buffer, merge4_non_pedestrian xml_buffer, merge4_physical_id xml_buffer, merge4_radius_arc xml_buffer, merge4_segment_count xml_buffer, merge4_segment_id xml_buffer, merge4_segment_type xml_buffer, merge4_sequence_number xml_buffer, merge4_snow_priority xml_buffer, merge4_street_code xml_buffer, merge4_traffic_direction xml_buffer, merge4_traffic_direction_source xml_buffer, merge_bike_lane xml_buffer, merge_citygml_class xml_buffer, merge_citygml_function xml_buffer, merge_construction_status xml_buffer,
      merge_curve_flag xml_buffer, merge_face_code xml_buffer, merge_gml_name xml_buffer, merge_level_end_segment xml_buffer, merge_level_start_segment xml_buffer, merge_non_pedestrian xml_buffer, merge_physical_id xml_buffer, merge_radius_arc xml_buffer, merge_sanitation_district_boundary_indicator xml_buffer, merge_segment_count xml_buffer, merge_segment_id xml_buffer, merge_segment_type xml_buffer, merge_sequence_number xml_buffer, merge_snow_priority xml_buffer, merge_street_code xml_buffer, merge_traffic_direction xml_buffer, merge_traffic_direction_source xml_buffer, node_id_from xml_buffer, node_id_to xml_buffer, non_pedestrian xml_buffer, physical_id xml_buffer, radius_arc xml_buffer, sanitation_district_boundary_indicator xml_buffer, segment_count xml_buffer, segment_id xml_buffer, segment_type xml_buffer, sequence_number xml_buffer, snow_priority xml_buffer, special_address_place_name xml_buffer, special_address_place_name_2 xml_buffer,
      special_address_place_name_3 xml_buffer, special_address_place_name_4 xml_buffer, special_address_place_name_5 xml_buffer, special_address_place_name_6 xml_buffer, special_address_place_name_7 xml_buffer, special_address_place_name_8 xml_buffer, special_address_place_name_9 xml_buffer, special_address_type xml_buffer, special_address_type_2 xml_buffer, special_address_type_3 xml_buffer, special_address_type_4 xml_buffer, special_address_type_5 xml_buffer, special_address_type_6 xml_buffer, special_address_type_7 xml_buffer, special_address_type_8 xml_buffer, special_address_type_9 xml_buffer, street_area_2D_sq_m xml_buffer, street_code xml_buffer, street_length_2D_meter xml_buffer, street_width_meter xml_buffer, traffic_direction xml_buffer, traffic_direction_source xml_buffer
    -> Intersector_2
Track (reader CITYGML_2) [off]
    attributes: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

Bookmark: Centerlines
Intersector_2
    DUPLICATE_Z_NODES = No
    SEG_ATTR = _segments
    PERFORM_SELF_INTERSECTION = No
    MEASURE_TYPE = Continuous
    OV_ATTR = _overlaps
    DEAGGREGATE_INPUT = Yes
    SEPARATE_COLLINEAR_SEGMENTS = No
    GENERATE_LIST_DROP = NO
    ATTRS_ACCUM_MODE = Merge Attributes
    INTERSECTED -> AttributeRemover
AttributeRemover
    REMOVE_ATTRS = _segments,_overlaps
    -> AttributeCreator_3
AttributeCreator_3
    ATTR_TABLE:
      SET_TO citygml_creationDate = 2016-10-17
      SET_TO externalReference{0}.informationSystem = @Value(externalReference{0}.informationSystem)
      SET_TO externalReference{0}.externalObject.name = @Value(externalReference{0}.externalObject.name)
      SET_TO gml_parent_id = NYC
    -> FeatureMerger [REQUESTOR]

Bookmark: Merge Attributes
FeatureMerger
    REJECT_NULL_MISSING_KEYS = No
    IGNORE_NULLS = No
    JOIN_KEYS = @Value(segment_id) @Value(segment_id) AUTO
    PROCESS_DUPS = No
    SUPPLIERS_FIRST = No
    ATTR_CONFLICT_RES = Use Requestor
    MERGE_TYPE = Attributes Only
    ATTR_ACCUM_MODE = Merge Supplier
    MERGED -> FeatureMerger_3 [REQUESTOR]
    NOT_MERGED -> FeatureMerger_3 [REQUESTOR]
Note: Merge attributes via corresponding attribute value 'segment_id' / 'gml_name'
FeatureMerger_3
    REJECT_NULL_MISSING_KEYS = No
    IGNORE_NULLS = No
    JOIN_KEYS = @Value(segment_id) @Value(SegmentID) AUTO
    PROCESS_DUPS = No
    SUPPLIERS_FIRST = No
    ATTR_CONFLICT_RES = Use Requestor
    MERGE_TYPE = Attributes Only
    ATTR_ACCUM_MODE = Merge Supplier
    MERGED -> FeatureMerger_2 [REQUESTOR]
    NOT_MERGED -> FeatureMerger_2 [REQUESTOR]
FeatureMerger_2
    REJECT_NULL_MISSING_KEYS = No
    IGNORE_NULLS = No
    JOIN_KEYS = @Value(gml_name) @Value(gml_name) AUTO
    PROCESS_DUPS = No
    SUPPLIERS_FIRST = No
    ATTR_CONFLICT_RES = Use Requestor
    MERGE_TYPE = Attributes Only
    ATTR_ACCUM_MODE = Merge Supplier
    MERGED -> LineOnAreaOverlayer [LINE]
    NOT_MERGED -> LineOnAreaOverlayer [LINE]
    DUPLICATE_SUPPLIER -> Bufferer

Bookmark: LION 2016 with Number of Lanes
Centerline_LION16_Output (reader ESRISHAPE_3) [off]
    attributes: OBJECTID long, Street char(32), SAFStreetN char(32), FeatureTyp char(1), SegmentTyp char(1), IncExFlag char(1), RB_Layer char(1), NonPed char(1), TrafDir char(1), TrafSrc char(3), SpecAddr char(1), FaceCode char(4), SeqNum char(5), StreetCode char(6), SAFStreetC char(6), LGC1 char(2), LGC2 char(2), LGC3 char(2), LGC4 char(2), LGC5 char(2), LGC6 char(2), LGC7 char(2), LGC8 char(2), LGC9 char(2), BOE_LGC char(1), SegmentID char(7), SegCount char(1), LocStatus char(1), LZip char(5), RZip char(5),
      LBoro long, RBoro long, L_CD char(3), R_CD char(3), LATOMICPOL char(3), RATOMICPOL char(3), LCT2010 char(4), LCT2010Suf char(2), RCT2010 char(4), RCT2010Suf char(2), LCB2010 char(4), LCB2010Suf char(1), RCB2010 char(4), RCB2010Suf char(1), LCT2000 char(4), LCT2000Suf char(2), RCT2000 char(4), RCT2000Suf char(2), LCB2000 char(4), LCB2000Suf char(1), RCB2000 char(4), RCB2000Suf char(1), LCT1990 char(4), LCT1990Suf char(2), RCT1990 char(4), RCT1990Suf char(2), LAssmDist char(2), LElectDist char(3), RAssmDist char(2), RElectDist char(3),
      SplitElect char(1), LSchlDist char(2), RSchlDist char(2), SplitSchl char(1), LSubSect char(2), RSubSect char(2), SanDistInd char(1), MapFrom char(3), MapTo char(3), BoroBndry char(1), MH_RI_Flag char(1), XFrom long, YFrom long, XTo long, YTo long, ArcCenterX long, ArcCenterY long, CurveFlag char(1), Radius long, NodeIDFrom char(7), NodeIDTo char(7), NodeLevelF char(1), NodeLevelT char(1), ConParity char(1), Twisted char(1), RW_TYPE char(2), PhysicalID long, GenericID long, NYPDID char(7), FDNYID char(7),
      LBlockFace char(10), RBlockFace char(10), LegacyID char(7), Status char(1), StreetWidt double, StreetWi_1 char(1), BikeLane char(1), Snow_Prior char(1), Number_Tra char(2), Number_Par char(2), Number_Tot char(2), Carto_Disp char(20), FCC char(2), ROW_Type char(1), LLo_Hyphen char(7), LHi_Hyphen char(7), RLo_Hyphen char(7), RHi_Hyphen char(7), FromLeft long, ToLeft long, FromRight long, ToRight long, Join_ID char(15), SHAPE_Leng double
    -> AttributeKeeper_2

Bookmark: New LION Centerline Data
AttributeKeeper_2
    KEEP_ATTRS = Number_Par,Number_Tra,SegmentID,Number_Tot
    -> AttributeRenamer_2
Note: Rename relevant attributes and remove irrelevant attributes
AttributeRenamer_2
    ATTR_TABLE:
      RENAME_SET_DEFAULT Number_Par > number_parking_lanes
      RENAME_SET_DEFAULT Number_Tot > number_total_lanes
      RENAME_SET_DEFAULT Number_Tra > number_travel_lanes
    -> FeatureMerger_3 [SUPPLIER]

Bookmark: Speed Limits
speed_limit_WGS (reader ESRISHAPE_2) [off]
    attributes: street char(32), postvz_sl double, postvz_sg char(5), Shape_Leng double
    -> CsmapReprojector

Bookmark: Speed Limits
CsmapReprojector
    VERTICAL_HANDLING = Ignore heights and leave them unchanged
    INTERPOLATION_TYPE_NAME = Nearest Neighbor
    RASTER_CELL_SIZE = Preserve Cells
    DEST = EPSG:32118
    REPROJECTED -> AttributeRenamer
AttributeRenamer
    ATTR_TABLE:
      RENAME_SET_DEFAULT street > gml_name
      RENAME_SET_DEFAULT postvz_sl > street_speed_limit_mph
    -> AttributeCreator_2
AttributeCreator_2
    ATTR_TABLE:
      SET_TO street_speed_limit_km_h = @Evaluate(@Value(street_speed_limit_mph)*1.61
        )
      SET_TO externalReference{2}.informationSystem = http://www.nyc.gov/html/dot/html/about/vz_datafeeds.shtml#speed
      SET_TO externalReference{2}.externalObject.name = @Value(gml_name)
    -> AttributeKeeper
Note: Rename relevant attributes and remove irrelevant attributes
AttributeKeeper
    KEEP_ATTRS = externalReference{3}.externalObject.name,gml_name,externalReference{2}.informationSystem,externalReference{4}.externalObject.name,externalReference{2}.externalObject.name,externalReference{0}.informationSystem,street_speed_limit_km_h,externalReference{5}.externalObject.name,externalReference{0}.externalObject.name,externalReference{1}.externalObject.name,street_speed_limit_mph
    -> FeatureMerger_2 [SUPPLIER]

Bookmark: Duplicate speedlimits
Bufferer
    OFFSET = 0.00001
    CAP_STYLE = Round
    INTERP_SEGMENTS = 8
    BUFFERED -> LineOnAreaOverlayer [AREA]
Note: Check for duplicate 'gml_name' attributes (=> more than one speedlimit per street name) and assign speed limits by areal overlay.
LineOnAreaOverlayer
    OV_ATTR = _overlaps
    ATTR_CONFLICT_RES = Use Incoming
    DEAGGREGATE_INPUT = Yes
    ATTR_ACCUM_MODE = Merge Incoming
    LINE -> LineJoiner
LineJoiner
    BREAK = no
    TOPOLOGY = End noded
    ACCUM_ATTRS_NAME = Get Attributes From One Representative Feature
    GROUP_BY = segment_id
    PRESERVE = no
    LINES_AS_SEGMENTS = No
    CONSIDER_NODE_ELEVATION = no
    CONNECT_Z_MODE = First Wins
    LINE -> AttributeRemover_3
AttributeRemover_3
    REMOVE_ATTRS = GE_LoD1_zOffset,SegmentID,citygml_level_of_detail{1},_overlaps
    -> AttributeValueMapper_3

Bookmark: Translate Level-Values and force 3D
AttributeValueMapper_3
    SRC = level_start_segment
    VAL_ATTR = level_start_segment
    LUT = B,-20,§,0,*,0,D,-16,E,-12,H,-8,I,-4,M,0,N,4,O,8,P,12,Q,16,R,20,S,24,U,28,V,32,W,36,Y,40,Z,44
    DIRECTION = Forward (Source To Destination)
    -> AttributeValueMapper_2
Note: Translate character level values into numerical values. M = 0, +/- 4m per character. / Interpolate 3D
AttributeValueMapper_2
    SRC = level_end_segment
    VAL_ATTR = level_end_segment
    LUT = B,-20,D,-16,E,-12,H,-8,I,-4,M,0,N,4,O,8,P,12,Q,16,R,20,S,24,U,28,V,32,W,36,Y,40,Z,44,*,0,§,0
    DIRECTION = Forward (Source To Destination)
    -> 3DInterpolator_2
3DInterpolator_2
    ZENDATTR = @Value(level_end_segment)
    ZSTARTATTR = @Value(level_start_segment)
    -> LengthCalculator_2
LengthCalculator_2
    DIM = 2
    MULT = 1
    LEN_ATTR = street_length_3D_meter
    -> ExpressionEvaluator

Bookmark: Calculate Slope in [%]
Note: Calculate slope based on start and end height
ExpressionEvaluator
    VAL_ATTR = slope_percent
    EXPRESSION = @mult(@div(@abs(@sub(@Value(level_end_segment),@Value(level_start_segment))),@Value(street_length_2D_meter)),100)
    ACTION = Create New Attribute
    -> CityGMLGeometrySetter

Bookmark: Set Geometry
CityGMLGeometrySetter
    ROLE = cityObjectMember
    GEOM = lod0Network
    -> GeometryPropertySetter
GeometryPropertySetter
    OVERWRITE_CHOICE = Yes
    SRC_ATTRS = citygml_lod_name
    REMOVE_ATTRIBUTE = No
    SETTYPE_PARAM = Traits From Attributes
    SET -> Centerlines_3D
    SET -> Road (writer CITYGML_3)

Bookmark: All Centerlines with new Attributes 3D
Centerlines_3D: Inspector

Bookmark: Output all Centerlines with new Attributes
Road (writer CITYGML_3) [off]
    attributes: bike_lane xml_buffer, citygml_appearance{}.xlink_href xml_buffer, citygml_auxiliary_traffic_area{}.xlink_href xml_buffer, citygml_class xml_buffer, citygml_class_codeSpace xml_buffer, citygml_creationDate xml_date, citygml_feature_role xml_buffer, citygml_feature_role_attr_name xml_buffer, citygml_feature_role_attr_val xml_buffer, citygml_function{} xml_buffer, citygml_function{}.codeSpace xml_buffer, citygml_generalizes_to{}.xlink_href xml_buffer, citygml_level_of_detail{} xml_buffer, citygml_relative_to_terrain xml_char(33), citygml_relative_to_water xml_char(38), citygml_target_uri xml_buffer, citygml_terminationDate xml_date, citygml_traffic_area{}.xlink_href xml_buffer, citygml_usage{} xml_buffer, citygml_usage{}.codeSpace xml_buffer, construction_status xml_buffer, curve_flag xml_buffer, externalReference{}.externalObject.name xml_xml, externalReference{}.externalObject.uri xml_xml, externalReference{}.informationSystem xml_xml, externalReference{}.informationSystem  xml_char(200), face_code xml_buffer, gml_description xml_buffer, gml_name xml_buffer, level_end_segment xml_buffer,
      level_start_segment xml_buffer, merge_bike_lane xml_buffer, merge_citygml_class xml_buffer, merge_citygml_function xml_buffer, merge_construction_status xml_buffer, merge_curve_flag xml_buffer, merge_face_code xml_buffer, merge_gml_name xml_buffer, merge_level_end_segment xml_buffer, merge_level_start_segment xml_buffer, merge_non_pedestrian xml_buffer, merge_physical_id xml_buffer, merge_radius_arc xml_buffer, merge_sanitation_district_boundary_indicator xml_buffer, merge_segment_count xml_buffer, merge_segment_id xml_buffer, merge_segment_type xml_buffer, merge_sequence_number xml_buffer, merge_snow_priority xml_buffer, merge_street_code xml_buffer, merge_traffic_direction xml_buffer, merge_traffic_direction_source xml_buffer, merge2_citygml_class xml_buffer, merge2_citygml_function xml_buffer, merge2_construction_status xml_buffer, merge2_curve_flag xml_buffer, merge2_face_code xml_buffer, merge2_gml_name xml_buffer, merge2_level_end_segment xml_buffer, merge2_level_start_segment xml_buffer,
      merge2_non_pedestrian xml_buffer, merge2_physical_id xml_buffer, merge2_radius_arc xml_buffer, merge2_segment_count xml_buffer, merge2_segment_id xml_buffer, merge2_segment_type xml_buffer, merge2_sequence_number xml_buffer, merge2_snow_priority xml_buffer, merge2_street_code xml_buffer, merge2_traffic_direction xml_buffer, merge2_traffic_direction_source xml_buffer, merge3_citygml_class xml_buffer, merge3_citygml_function xml_buffer, merge3_construction_status xml_buffer, merge3_curve_flag xml_buffer, merge3_face_code xml_buffer, merge3_gml_name xml_buffer, merge3_level_end_segment xml_buffer, merge3_level_start_segment xml_buffer, merge3_non_pedestrian xml_buffer, merge3_physical_id xml_buffer, merge3_radius_arc xml_buffer, merge3_segment_count xml_buffer, merge3_segment_id xml_buffer, merge3_segment_type xml_buffer, merge3_sequence_number xml_buffer, merge3_snow_priority xml_buffer, merge3_street_code xml_buffer, merge3_traffic_direction xml_buffer, merge3_traffic_direction_source xml_buffer,
      merge4_citygml_class xml_buffer, merge4_citygml_function xml_buffer, merge4_construction_status xml_buffer, merge4_face_code xml_buffer, merge4_gml_name xml_buffer, merge4_level_end_segment xml_buffer, merge4_level_start_segment xml_buffer, merge4_non_pedestrian xml_buffer, merge4_physical_id xml_buffer, merge4_radius_arc xml_buffer, merge4_segment_count xml_buffer, merge4_segment_id xml_buffer, merge4_segment_type xml_buffer, merge4_sequence_number xml_buffer, merge4_snow_priority xml_buffer, merge4_street_code xml_buffer, merge4_traffic_direction xml_buffer, merge4_traffic_direction_source xml_buffer, node_id_from xml_buffer, node_id_to xml_buffer, non_pedestrian xml_buffer, number_parking_lanes xml_char(200), number_total_lanes xml_char(200), number_travel_lanes xml_char(200), physical_id xml_buffer, radius_arc xml_buffer, sanitation_district_boundary_indicator xml_buffer, segment_count xml_buffer, segment_id xml_buffer, segment_type xml_buffer,
      sequence_number xml_buffer, slope_percent xml_char(200), snow_priority xml_buffer, special_address_place_name xml_buffer, special_address_place_name_2 xml_buffer, special_address_place_name_3 xml_buffer, special_address_place_name_4 xml_buffer, special_address_place_name_5 xml_buffer, special_address_place_name_6 xml_buffer, special_address_place_name_7 xml_buffer, special_address_place_name_8 xml_buffer, special_address_place_name_9 xml_buffer, special_address_type xml_buffer, special_address_type_2 xml_buffer, special_address_type_3 xml_buffer, special_address_type_4 xml_buffer, special_address_type_5 xml_buffer, special_address_type_6 xml_buffer, special_address_type_7 xml_buffer, special_address_type_8 xml_buffer, special_address_type_9 xml_buffer, street_area_2D_sq_m xml_buffer, street_code xml_buffer, street_length_2D_meter xml_buffer, street_length_3D_meter xml_char(200), street_pavement_rating_date xml_char(200), street_pavement_rating_num xml_char(200), street_pavement_rating_text xml_char(200), street_segment_width_meter xml_char(200), street_speed_limit_km_h xml_char(200),
      street_speed_limit_mph xml_char(200), street_width_meter xml_buffer, traffic_direction xml_buffer, traffic_direction_source xml_buffer

Bookmark: Input Data
Note: Information on Pavement Ratings
Note: Ceterline street data for a test area in Manhattan
Note: Centerline data for the entire city
Note: LION 2016 (with additional attributes such as 'number of lanes')
Note: Information on Speed Limits

FME custom transformer CityGMLGeometrySetter
This transformer provides a convenient way to set both the CityGML LOD Name and role from a preset list of options.
Input Ports
    Input
    Features to tag with City LOD name and feature role 
    Output Ports
    Output
    Features tagged with City LOD name and feature role 
    Parameters
    CityGML Lod Name
    Select the desired CityGML Lod name
    Feature Role
    Select the desired feature role

Parameters:
- GEOM =   # CityGML Lod Name
- ROLE =   # Feature Role

INPUT (input)
    -> AttributeCreator
Note: Set LOD name / and citygml role
AttributeCreator
    ATTR_TABLE:
      SET_TO citygml_lod_name = $(GEOM)
      SET_TO citygml_feature_role = $(ROLE)
    -> GeometryPropertySetter
Note: Convert LOD to geometry trait
GeometryPropertySetter
    OVERWRITE_CHOICE = Yes
    SRC_ATTRS = citygml_lod_name
    REMOVE_ATTRIBUTE = No
    SETTYPE_PARAM = Traits From Attributes
    SET -> OUTPUT (output)
OUTPUT (output)
