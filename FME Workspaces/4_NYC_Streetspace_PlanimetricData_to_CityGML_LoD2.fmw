FME workspace 4_NYC_Streetspace_PlanimetricData_to_CityGML_LoD2.fmw

Parameters:
- SourceDataset_CITYGML = H:\TUM Geoinformatik\City Model NYC\Datengrundlage\Mittelachsen CityGML\Centerlines_unfiltered.gml   # Source CityGML File(s)
- SourceDataset_ESRISHAPE = H:\TUM Geoinformatik\City Model NYC\Datengrundlage\Daten Clipped\Roadbed_Extract\Roadbed_Extract.shp   # Source Esri Shapefile(s)
- SourceDataset_ESRISHAPE_33 = H:\TUM Geoinformatik\City Model NYC\Datengrundlage\Daten Clipped\Sidewalks_Extract\Sidewalks_Extract.shp   # Source Esri Shapefile(s)
- SourceDataset_ESRISHAPE_25 = H:\TUM Geoinformatik\City Model NYC\Datengrundlage\Daten Clipped\Median_Extract\Median_Extract.shp   # Source Esri Shapefile(s)
- SourceDataset_ESRISHAPE_21 = H:\TUM Geoinformatik\City Model NYC\Datengrundlage\Daten Clipped\Curbs_Extract\Curbs_Extract.shp   # Source Esri Shapefile(s)
- SourceDataset_ESRISHAPE_29 = H:\TUM Geoinformatik\City Model NYC\Datengrundlage\Daten Clipped\Parking_Lots_Extract\Parking_Lots_Extract.shp   # Source Esri Shapefile(s)
- SourceDataset_ESRISHAPE_19 = H:\TUM Geoinformatik\City Model NYC\Datengrundlage\Daten Clipped\Plazas_Extract\Plazas_Extract.shp   # Source Esri Shapefile(s)
- SourceDataset_ESRISHAPE_23 = H:\TUM Geoinformatik\City Model NYC\Datengrundlage\Testgebiet_Kreisverkehr\Roadbed_Kreisverkehr\Roadbed.shp   # Source Esri Shapefile(s)
- SourceDataset_ESRISHAPE_27 = H:\TUM Geoinformatik\City Model NYC\Datengrundlage\Testgebiet_Kreisverkehr\Median_Kreisverkehr\Median.shp   # Source Esri Shapefile(s)
- SourceDataset_ESRISHAPE_31 = H:\TUM Geoinformatik\City Model NYC\Datengrundlage\Testgebiet_Kreisverkehr\Sidewalk_Kreisverkehr\Sidewalk.shp   # Source Esri Shapefile(s)
- SourceDataset_ESRISHAPE_35 = H:\TUM Geoinformatik\City Model NYC\Datengrundlage\Testgebiet_Kreisverkehr\Curbs_Kreisverkehr\Curbs.shp   # Source Esri Shapefile(s)
- SourceDataset_ESRISHAPE_20 = H:\TUM Geoinformatik\City Model NYC\Datengrundlage\Testgebiet_Kreisverkehr\Parking_Lot_Kreisverkehr\Parking_Lot.shp   # Source Esri Shapefile(s)
- SourceDataset_ESRISHAPE_22 = H:\TUM Geoinformatik\City Model NYC\Datengrundlage\Testgebiet_Kreisverkehr\Plaza_Kreisverkehr\Plaza.shp   # Source Esri Shapefile(s)
- DestDataset_CITYGML = C:\NYC Streetspace Data for Web Map Client\Roadbed\Road.gml   # Destination CityGML Document
- DestDataset_CITYGML_14 = C:\NYC Streetspace Data for Web Map Client\Intersection\Road.gml   # Destination CityGML Document
- DestDataset_CITYGML_22 = C:\NYC Streetspace Data for Web Map Client\Median_Painted\Road.gml   # Destination CityGML Document
- DestDataset_CITYGML_16 = C:\NYC Streetspace Data for Web Map Client\Median_Raised\Road.gml   # Destination CityGML Document
- DestDataset_CITYGML_20 = C:\NYC Streetspace Data for Web Map Client\Median_Grass\Road.gml   # Destination CityGML Document
- DestDataset_CITYGML_13 = C:\NYC Streetspace Data for Web Map Client\Plaza\Square.gml   # Destination CityGML Document
- DestDataset_CITYGML_15 = C:\NYC Streetspace Data for Web Map Client\Parking_Lot\Square.gml   # Destination CityGML Document
- DestDataset_CITYGML_19 = C:\NYC Streetspace Data for Web Map Client\Track\Track.gml   # Destination CityGML Document
- DestDataset_CITYGML_21 = C:\Sidewalk   # Destination CityGML Document
- SourceDataset_ESRISHAPE_24 = H:\TUM Geoinformatik\City Model NYC\Datengrundlage\Planimetrics\Roadbed\geo_export_bfdefa9a-cc02-458e-bbef-f4d029ad2173.shp   # Source Esri Shapefile(s)
- SourceDataset_ESRISHAPE_26 = H:\TUM Geoinformatik\City Model NYC\Datengrundlage\Planimetrics\Median\geo_export_fdd96682-a3f5-423d-934a-be8242715d24.shp   # Source Esri Shapefile(s)
- SourceDataset_ESRISHAPE_28 = H:\TUM Geoinformatik\City Model NYC\Datengrundlage\Planimetrics\Sidewalk\geo_export_a5eb0ecf-19f8-45cf-813d-646313d270cb.shp   # Source Esri Shapefile(s)
- SourceDataset_ESRISHAPE_30 = H:\TUM Geoinformatik\City Model NYC\Datengrundlage\Planimetrics\Curbs\geo_export_b101ce9c-6658-4c67-89c9-c70a93092179.shp   # Source Esri Shapefile(s)
- SourceDataset_ESRISHAPE_32 = H:\TUM Geoinformatik\City Model NYC\Datengrundlage\Planimetrics\Parking Lot\geo_export_35797fb0-5c4b-4b55-a75b-a3e1994e74e2.shp   # Source Esri Shapefile(s)
- SourceDataset_ESRISHAPE_34 = H:\TUM Geoinformatik\City Model NYC\Datengrundlage\Planimetrics\Plazas\geo_export_32cd10fe-3282-4fa7-997d-c0add45dda5d.shp   # Source Esri Shapefile(s)
- DestDataset_CITYGML_12 = E:\TUM Geoinformatik\City Model NYC\Output\Road.gml   # Destination CityGML Document

Readers:
- CITYGML_1: CITYGML from $(SourceDataset_CITYGML)
- ESRISHAPE_1: ESRISHAPE from $(SourceDataset_ESRISHAPE)
- ESRISHAPE_2: ESRISHAPE from $(SourceDataset_ESRISHAPE_33)
- ESRISHAPE_3: ESRISHAPE from $(SourceDataset_ESRISHAPE_25)
- ESRISHAPE_4: ESRISHAPE from $(SourceDataset_ESRISHAPE_21)
- ESRISHAPE_5: ESRISHAPE from $(SourceDataset_ESRISHAPE_29)
- ESRISHAPE_6: ESRISHAPE from $(SourceDataset_ESRISHAPE_19)
- ESRISHAPE_7: ESRISHAPE from $(SourceDataset_ESRISHAPE_23)
- ESRISHAPE_8: ESRISHAPE from $(SourceDataset_ESRISHAPE_27)
- ESRISHAPE_9: ESRISHAPE from $(SourceDataset_ESRISHAPE_31)
- ESRISHAPE_10: ESRISHAPE from $(SourceDataset_ESRISHAPE_35)
- ESRISHAPE_11: ESRISHAPE from $(SourceDataset_ESRISHAPE_20)
- ESRISHAPE_12: ESRISHAPE from $(SourceDataset_ESRISHAPE_22)
- ESRISHAPE_13: ESRISHAPE from $(SourceDataset_ESRISHAPE_24)
- ESRISHAPE_14: ESRISHAPE from $(SourceDataset_ESRISHAPE_26)
- ESRISHAPE_15: ESRISHAPE from $(SourceDataset_ESRISHAPE_28)
- ESRISHAPE_16: ESRISHAPE from $(SourceDataset_ESRISHAPE_30)
- ESRISHAPE_17: ESRISHAPE from $(SourceDataset_ESRISHAPE_32)
- ESRISHAPE_18: ESRISHAPE from $(SourceDataset_ESRISHAPE_34)

Writers:
- CITYGML_2: CITYGML to $(DestDataset_CITYGML)
- CITYGML_3: CITYGML to $(DestDataset_CITYGML_14)
- CITYGML_4: CITYGML to $(DestDataset_CITYGML_22)
- CITYGML_5: CITYGML to $(DestDataset_CITYGML_16)
- CITYGML_6: CITYGML to $(DestDataset_CITYGML_20)
- CITYGML_7: CITYGML to $(DestDataset_CITYGML_13)
- CITYGML_8: CITYGML to $(DestDataset_CITYGML_15)
- CITYGML_9: CITYGML to $(DestDataset_CITYGML_19)
- CITYGML_10: CITYGML to $(DestDataset_CITYGML_21)
- CITYGML_11: CITYGML to $(DestDataset_CITYGML_12)

CsmapReprojector
    RASTER_CELL_SIZE = Preserve Cells
    VERTICAL_HANDLING = Ignore heights and leave them unchanged
    DEST = EPSG:32118
    INTERPOLATION_TYPE_NAME = Nearest Neighbor
    REPROJECTED -> Tester
    REPROJECTED -> Tester_12
Note: Seperate 'Intersection' and 'Roadbed' objects
Tester
    TEST_CLAUSE = TEST @Value(sub_code) = 350000
    TEST_MODE = Automatic
    TEST_DESCRIPTION = ""
    BOOL_OP = OR
    PASSED -> LineOnAreaOverlayer [AREA]
    PASSED -> LineOnAreaOverlayer_2 [AREA]
Tester_12
    TEST_CLAUSE = TEST @Value(sub_code) = 350010
    TEST_MODE = Automatic
    TEST_DESCRIPTION = ""
    BOOL_OP = OR
    PASSED -> FeatureColorSetter_3
    PASSED -> LineOnAreaOverlayer_6 [AREA]
FeatureColorSetter_3
    FILL_COLOR = 0.521569,0.784314,0.784314
    COLOR = 0,0,0
    MODE = Fixed
    COLORED -> AreaOnAreaOverlayer_5 [AREA]
    COLORED -> LineOnAreaOverlayer_7 [AREA]
CsmapReprojector_3
    RASTER_CELL_SIZE = Preserve Cells
    VERTICAL_HANDLING = Ignore heights and leave them unchanged
    DEST = EPSG:32118
    INTERPOLATION_TYPE_NAME = Nearest Neighbor
    REPROJECTED -> AreaOnAreaOverlayer_4 [AREA]
CsmapReprojector_2
    RASTER_CELL_SIZE = Preserve Cells
    VERTICAL_HANDLING = Ignore heights and leave them unchanged
    DEST = EPSG:32118
    INTERPOLATION_TYPE_NAME = Nearest Neighbor
    REPROJECTED -> TestFilter
    REPROJECTED -> AreaOnAreaOverlayer_4 [AREA]
    REPROJECTED -> Tester_15
AreaOnAreaOverlayer_4
    CONNECT_Z_MODE = First Wins
    OVC_ATTR = _overlaps
    ACCUM_ATTRS_NAME = Get Attributes From One Representative Feature
    AREA -> Tester_17
Tester_17
    TEST_CLAUSE:
      TEST @Value(_overlaps) = 1
      TEST @Value(feat_code) = 3600
    TEST_MODE = Automatic
    TEST_DESCRIPTION = ""
    BOOL_OP = AND
    PASSED -> AreaOnAreaOverlayer_2 [AREA]
Tester_15
    TEST_CLAUSE = TEST @Value(sub_code) = 380000
    TEST_MODE = Automatic
    TEST_DESCRIPTION = ""
    BOOL_OP = OR
    PASSED -> AreaOnAreaOverlayer_3 [AREA]
Note: Input data for the entire city
Note: Input data for a smaller test area in Brooklyn
Note: Input data for a smaller test area in central manhattan
Note: Dieser Workspace wurde im Rahmen der Masterarbeit "Detaillierte Repräsentation des Straßenraums in 3D-Stadtmodellen" erstellt. / C. Beil / 2016 / https://www.gis.bgu.tum.de
AttributeExposer
    ATTR_LIST = externalReference{1}.externalObject.name
    -> AttributeKeeper_8
    -> LineOnAreaOverlayer [LINE]
    -> LineOnAreaOverlayer_7 [LINE]
Roadbed: Inspector
Road (writer CITYGML_2) [off]
    attributes: bike_lane xml_buffer, citygml_appearance{}.xlink_href xml_buffer, citygml_auxiliary_traffic_area{}.xlink_href xml_buffer, citygml_class xml_buffer, citygml_creationDate xml_date, citygml_feature_role xml_buffer, citygml_feature_role_attr_name xml_buffer, citygml_feature_role_attr_val xml_buffer, citygml_function{} xml_buffer, citygml_function{0} xml_char(200), citygml_generalizes_to{}.xlink_href xml_buffer, citygml_level_of_detail{} xml_buffer, citygml_level_of_detail{0} xml_char(200), citygml_surfaceMaterial xml_char(200), citygml_target_uri xml_buffer, citygml_terminationDate xml_date, citygml_traffic_area{}.xlink_href xml_buffer, citygml_usage{} xml_buffer, citygml_usage{0} xml_char(200), construction_status xml_buffer, curve_flag xml_buffer, externalReference{}.externalObject.name xml_xml, externalReference{}.externalObject.uri xml_xml, externalReference{}.informationSystem xml_xml, externalReference{1}.externalObject.name xml_xml, externalReference{1}.informationSystem xml_xml, face_code xml_buffer, gml_description xml_buffer, gml_name xml_buffer, level_end_segment xml_buffer,
      level_start_segment xml_buffer, node_id_from xml_buffer, node_id_to xml_buffer, number_parking_lanes xml_buffer, number_total_lanes xml_buffer, number_travel_lanes xml_buffer, orientation xml_char(200), physical_id xml_buffer, radius_arc xml_buffer, road_id xml_char(200), sanitation_district_boundary_indicator xml_buffer, segment_count xml_buffer, segment_id xml_buffer, segment_type xml_buffer, sequence_number xml_buffer, slope_percent xml_buffer, snow_priority xml_buffer, special_address_place_name xml_buffer, special_address_place_name_2 xml_buffer, special_address_place_name_3 xml_buffer, special_address_place_name_4 xml_buffer, special_address_place_name_5 xml_buffer, special_address_type xml_buffer, special_address_type_2 xml_buffer, special_address_type_3 xml_buffer, special_address_type_4 xml_buffer, special_address_type_5 xml_buffer, street_area_3D_sqm xml_char(200), street_code xml_buffer, street_length_3D_meter xml_buffer,
      street_pavement_rating_date xml_buffer, street_pavement_rating_num xml_buffer, street_pavement_rating_text xml_buffer, street_speed_limit_km_h xml_buffer, street_speed_limit_mph xml_buffer, street_width_meter xml_buffer, traffic_direction xml_buffer, traffic_direction_source xml_buffer
AttributeKeeper_2
    KEEP_ATTRS = road_id,gml_name
    -> NeighborFinder_4 [CANDIDATE]
Curbs: Inspector
Road (writer CITYGML_11) [off]
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer
Median_Painted: Inspector
Road (writer CITYGML_4) [off]
    attributes: citygml_class xml_buffer, citygml_creationDate xml_date, citygml_feature_role xml_buffer, citygml_feature_role_attr_name xml_buffer, citygml_feature_role_attr_val xml_buffer, citygml_function{0} xml_char(200), citygml_level_of_detail{0} xml_char(200), citygml_surfaceMaterial xml_char(200), citygml_target_uri xml_buffer, citygml_terminationDate xml_date, citygml_usage{0} xml_char(200), externalReference{0}.externalObject.name xml_xml, externalReference{0}.informationSystem xml_xml, gml_name xml_buffer, median_area_sqm xml_char(200), road_id xml_char(200)
Median_Raised: Inspector
Road (writer CITYGML_5) [off]
    attributes: citygml_class xml_buffer, citygml_creationDate xml_date, citygml_feature_role xml_buffer, citygml_feature_role_attr_name xml_buffer, citygml_feature_role_attr_val xml_buffer, citygml_function{0} xml_char(200), citygml_level_of_detail{0} xml_char(200), citygml_surfaceMaterial xml_char(200), citygml_target_uri xml_buffer, citygml_terminationDate xml_date, externalReference{0}.externalObject.name xml_char(200), externalReference{0}.informationSystem xml_char(200), gml_name xml_buffer, median_area_sqm xml_char(200), median_height_inch xml_char(200), median_height_meter xml_char(200), median_volume_cubicmeter xml_char(200), road_id xml_char(200)
Grass: Inspector
Road (writer CITYGML_6) [off]
    attributes: citygml_class xml_buffer, citygml_creationDate xml_date, citygml_feature_role xml_buffer, citygml_feature_role_attr_name xml_buffer, citygml_feature_role_attr_val xml_buffer, citygml_level_of_detail{0} xml_char(200), citygml_surfaceMaterial xml_char(200), citygml_target_uri xml_buffer, citygml_terminationDate xml_date, externalReference{0}.externalObject.name xml_xml, externalReference{0}.informationSystem xml_xml, gml_name xml_buffer, median_area_sqm xml_char(200), median_height_inch xml_char(200), median_height_meter xml_char(200), road_id xml_char(200)
Plaza: Inspector
Square (writer CITYGML_7) [off]
    attributes: citygml_class xml_char(200), citygml_creationDate xml_date, citygml_feature_role xml_buffer, citygml_function{0} xml_char(200), citygml_surfaceMaterial xml_char(200), citygml_target_uri xml_buffer, citygml_usage{0} xml_char(200), externalReference{0}.externalObject.name xml_xml, externalReference{0}.informationSystem xml_xml, gml_name xml_buffer, plaza_area_sqm xml_char(200), plaza_height_inch xml_char(200), plaza_height_meter xml_char(200), plaza_volume_cubicmeter xml_char(200), square_id xml_char(200), surfaceType xml_char(200)

Bookmark: Input Data Gesamtgebiet
Note: Roadbed
geo_export_bfdefa9a-cc02-458e-bbef-f4d029ad2173 (reader ESRISHAPE_13) [off]
    attributes: shape_area number(33,31), source_id number(33,31), shape_leng number(33,31), status char(254), feat_code number(33,31), sub_code number(33,31)
    -> CsmapReprojector
Note: Median
geo_export_fdd96682-a3f5-423d-934a-be8242715d24 (reader ESRISHAPE_14) [off]
    attributes: feat_code number(33,31), shape_area number(33,31), status char(254), source_id number(33,31), street_nam char(254), shape_leng number(33,31), sub_code number(33,31)
    -> CsmapReprojector_3
Note: Sidewalk
geo_export_a5eb0ecf-19f8-45cf-813d-646313d270cb (reader ESRISHAPE_15) [off]
    attributes: status char(254), source_id number(33,31), feat_code number(33,31), shape_area number(33,31), sub_code number(33,31), shape_leng number(33,31)
    -> CsmapReprojector_2
Note: Curb
geo_export_b101ce9c-6658-4c67-89c9-c70a93092179 (reader ESRISHAPE_16) [off]
    attributes: sub_code number(33,31), source_id number(33,31), shape_leng number(33,31), status char(254), feat_code number(33,31)
    -> CsmapReprojector_4
Note: Parking Lot
geo_export_35797fb0-5c4b-4b55-a75b-a3e1994e74e2 (reader ESRISHAPE_17) [off]
    attributes: source_id number(33,31), shape_leng number(33,31), shape_area number(33,31), status char(254), sub_code number(33,31), feat_code number(33,31)
    -> CsmapReprojector_5
Note: Plaza
geo_export_32cd10fe-3282-4fa7-997d-c0add45dda5d (reader ESRISHAPE_18) [off]
    attributes: status char(254), feat_code number(33,31), shape_leng number(33,31), shape_area number(33,31), source_id number(33,31), sub_code number(33,31)
    -> CsmapReprojector_6

Bookmark: Input Data Bartel Pritchard Square
Roadbed (reader ESRISHAPE_7) [off]
    attributes: shape_area number(33,31), source_id number(33,31), shape_leng number(33,31), status char(254), feat_code number(33,31), sub_code number(33,31)
    -> CsmapReprojector
Median (reader ESRISHAPE_8) [off]
    attributes: feat_code number(33,31), shape_area number(33,31), status char(254), source_id number(33,31), street_nam char(254), shape_leng number(33,31), sub_code number(33,31)
    -> CsmapReprojector_3
Sidewalk (reader ESRISHAPE_9) [off]
    attributes: status char(254), source_id number(33,31), feat_code number(33,31), shape_area number(33,31), sub_code number(33,31), shape_leng number(33,31)
    -> CsmapReprojector_2
Curbs (reader ESRISHAPE_10) [off]
    attributes: sub_code number(33,31), source_id number(33,31), shape_leng number(33,31), status char(254), feat_code number(33,31)
    -> CsmapReprojector_4
Parking_Lot (reader ESRISHAPE_11) [off]
    attributes: source_id number(33,31), shape_leng number(33,31), shape_area number(33,31), status char(254), sub_code number(33,31), feat_code number(33,31)
    -> CsmapReprojector_5
Plaza (reader ESRISHAPE_12) [off]
    attributes: status char(254), feat_code number(33,31), shape_leng number(33,31), shape_area number(33,31), source_id number(33,31), sub_code number(33,31)
    -> CsmapReprojector_6

Bookmark: Roadbed Manhattan Shape
Roadbed_Extract (reader ESRISHAPE_1) [off]
    attributes: shape_area number(33,31), source_id number(33,31), shape_leng number(33,31), status char(254), feat_code number(33,31), sub_code number(33,31)
    -> CsmapReprojector

Bookmark: Median Manhattan Shape
Median_Extract (reader ESRISHAPE_3) [off]
    attributes: feat_code number(33,31), shape_area number(33,31), status char(254), source_id number(33,31), street_nam char(254), shape_leng number(33,31), sub_code number(33,31)
    -> CsmapReprojector_3

Bookmark: Sidewalk Manhattan Shape
Sidewalks_Extract (reader ESRISHAPE_2) [off]
    attributes: status char(254), source_id number(33,31), feat_code number(33,31), shape_area number(33,31), sub_code number(33,31), shape_leng number(33,31)
    -> CsmapReprojector_2

Bookmark: Edit Sidewalks
TestFilter
    DEFAULT_VALUE = <UNFILTERED>
    TEST_LIST = BOOL_OP,OR,COMPOSITE_TEST,<Unused>,TEST_CLAUSE,"TEST @Value(sub_code) = 380000",Row_Sidewalk,BOOL_OP,OR,COMPOSITE_TEST,<Unused>,TEST_CLAUSE,"TEST @Value(sub_code) = 380010",Interior_Sidewalk
    Row_Sidewalk -> AttributeKeeper_11
    Interior_Sidewalk -> AttributeKeeper_23
AttributeKeeper_11
    KEEP_ATTRS = source_id
    -> Chopper_2
Chopper_2
    MAX_VERTICES = 4
    REMNANT_ATTR = _remnant
    CHOPPED_ATTR = _chopped
    MODE = By Vertex
    -> NeighborFinder_3 [BASE]
AttributeKeeper_23
    KEEP_ATTRS = source_id,sub_code
    -> AttributeCreator_26
AttributeCreator_26
    ATTR_TABLE:
      SET_TO citygml_class = @Value(sub_code)
      SET_TO citygml_function{0} = 2
      SET_TO citygml_surfaceMaterial = 9999
      SET_TO citygml_creationDate = 2016-12-01
      SET_TO citygml_level_of_detail{0} = 3
      SET_TO citygml_target_uri = http://www.opengis.net/citygml/transportation/2.0
      SET_TO id = id_
      SET_TO sidewalk_height_meter = 0
      SET_TO sidewalk_height_inch = 0
      SET_TO gml_parent_id = NYC
      SET_TO gml_name = Track
      SET_TO externalReference{0}.informationSystem = https://data.cityofnewyork.us/City-Government/Sidewalk/vfx9-tbb6/data
      SET_TO citygml_usage{0} = 1
      SET_TO externalReference{0}.externalObject.name = @Value(source_id)
    -> UUIDGenerator_16
UUIDGenerator_16
    UUID_ATTR = _uuid
    -> StringConcatenator_16
StringConcatenator_16
    ACTION = Create New Attribute
    VAL_ATTR = gml_id
    PARM_LINE = @Value(id)@Value(_uuid)
    -> Orientor_5
Orientor_5
    KIND = LEFT_HAND_RULE
    ORIENTED -> FaceReplacer_8
FaceReplacer_8
    THICKNESS_TOLERANCE_CHOICE = Automatic
    ANGULAR_TOLERANCE = 0.0
    THICKNESS_TOLERANCE = 0.0
    ANGULAR_TOLERANCE_CHOICE = Automatic
    -> GeometryColorSetter_12
GeometryColorSetter_12
    FILL_COLOR = 0.623529,0.623529,0.623529
    SIDE = Front
    MODE = Fixed
    ALPHA = 1
    COLORED -> Aggregator_16
Aggregator_16
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeRemover_25
AttributeRemover_25
    REMOVE_ATTRS = _part_number,_hierarchy_id,_hierarchy_child_id_list{0},_geometry_name,_hierarchy_parent_id
    -> AttributeCreator_25
AttributeCreator_25
    ATTR_TABLE = SET_TO track_id = track_@Value(gml_id)
    -> AttributeCreator_32
AttributeCreator_32
    ATTR_TABLE = SET_TO gml_parent_id = @Value(track_id)
    -> CityGMLGeometrySetter_15
CityGMLGeometrySetter_15
    ROLE = trafficArea
    GEOM = lod3MultiSurface
    -> GeometryPropertySetter_16
GeometryPropertySetter_16
    SRC_ATTRS = citygml_lod_name
    OVERWRITE_CHOICE = Yes
    SETTYPE_PARAM = Traits From Attributes
    REMOVE_ATTRIBUTE = No
    SET -> AttributeRemover
AttributeRemover
    REMOVE_ATTRS = _uuid,source_id,sub_code,id
    -> Track (writer CITYGML_9)
    -> Track
Track: Inspector
Track (writer CITYGML_9) [off]
    attributes: citygml_class xml_char(200), citygml_creationDate xml_date, citygml_feature_role xml_buffer, citygml_function{0} xml_char(200), citygml_level_of_detail{0} xml_char(200), citygml_surfaceMaterial xml_char(200), citygml_target_uri xml_buffer, citygml_usage{0} xml_char(200), externalReference{0}.externalObject.name xml_xml, externalReference{0}.informationSystem xml_xml, gml_name xml_buffer, sidewalk_height_inch xml_char(200), sidewalk_height_meter xml_char(200), track_id xml_char(200)
NeighborFinder_3
    ATTR_ACCUM_MODE = Merge Candidate
    TREAT_POLYGON_AS = Areas
    CANDIDATES_FIRST = No
    K = 1
    ATTR_CONFLICT_RES = Use Base
    MODE = Bases and Candidates
    INSERT_VERTEX = No
    MATCHED -> Dissolver_2
Dissolver_2
    GROUP_BY = segment_id
    ACCUM_INPUT_ATTRS = Get Attributes From One Representative Feature
    CONNECT_Z_MODE = First Wins
    NO_OVRLP = No
    AREA -> AreaCalculator_4
AreaCalculator_4
    AREA_ATTR = _area
    AREA_TYPE = Plane Area
    MULT = 1
    -> Tester_20
Tester_20
    TEST_CLAUSE = TEST @Value(_area) < 50
    TEST_MODE = Automatic
    TEST_DESCRIPTION = ""
    BOOL_OP = OR
    PASSED -> AttributeKeeper_12
    FAILED -> Dissolver_3
    FAILED -> NeighborFinder_2 [CANDIDATE]
AttributeKeeper_12
    -> NeighborFinder_2 [BASE]
NeighborFinder_2
    ATTR_ACCUM_MODE = Only Use Candidate
    TREAT_POLYGON_AS = Areas
    CANDIDATES_FIRST = No
    K = 1
    MODE = Bases and Candidates
    INSERT_VERTEX = No
    MATCHED -> Dissolver_3
Dissolver_3
    GROUP_BY = segment_id
    ACCUM_INPUT_ATTRS = Get Attributes From One Representative Feature
    CONNECT_Z_MODE = First Wins
    NO_OVRLP = No
    AREA -> AttributeKeeper_13
AttributeKeeper_13
    KEEP_ATTRS = _area,road_id,source_id,gml_name,segment_id
    KEEP_LIST = citygml_appearance{} citygml_appearance{}.xlink_href citygml_auxiliary_traffic_area{} citygml_auxiliary_traffic_area{}.xlink_href citygml_function{} citygml_generalizes_to{} citygml_generalizes_to{}.xlink_href citygml_level_of_detail{} citygml_traffic_area{} citygml_traffic_area{}.xlink_href citygml_usage{} externalReference{} externalReference{}.externalObject.name externalReference{}.externalObject.uri externalReference{}.informationSystem
    -> AttributeRenamer_7
AttributeRenamer_7
    ATTR_TABLE:
      RENAME_SET_DEFAULT gml_name > sidewalk_adjacent_street_name
      RENAME_SET_DEFAULT segment_id > sidewalk_adjacent_segmentID
      RENAME_SET_DEFAULT _area > sidewalk_area_3D_sqm
      RENAME_SET_DEFAULT source_id > externalReference{0}.externalObject.name
    -> AreaOnAreaOverlayer_8 [AREA]
Tester_21
    TEST_CLAUSE = TEST @Value(sub_code1) = 225000
    TEST_MODE = Automatic
    TEST_DESCRIPTION = ""
    BOOL_OP = OR
    FAILED -> AttributeCreator_19
AttributeCreator_19
    ATTR_TABLE:
      SET_TO citygml_class = 380000
      SET_TO citygml_function0 = 2
      SET_TO citygml_surfaceMaterial = 9999
      SET_TO citygml_creationDate = 2016-12-01
      SET_TO citygml_level_of_detail{0} = 3
      SET_TO citygml_target_uri = http://www.opengis.net/citygml/transportation/2.0
      SET_TO id = id_
      SET_TO sidewalk_height_meter = 0.1524
      SET_TO sidewalk_height_inch = 6
      SET_TO gml_name = @Value(sidewalk_adjacent_street_name)
      SET_TO externalReference{0}.informationSystem = https://data.cityofnewyork.us/City-Government/Sidewalk/vfx9-tbb6/data
      SET_TO citygml_usage0 = 1
      SET_TO externalReference{0}.externalObject.name = @Value(externalReference{0}.externalObject.name)
    -> UUIDGenerator_4
UUIDGenerator_4
    UUID_ATTR = _uuid
    -> StringConcatenator_4
StringConcatenator_4
    ACTION = Create New Attribute
    VAL_ATTR = gml_id
    PARM_LINE = @Value(id)@Value(_uuid)
    -> AreaCalculator_5
AreaCalculator_5
    AREA_ATTR = sidewalk_area_sqm
    AREA_TYPE = Plane Area
    MULT = 1
    -> AttributeRounder_9
AttributeRounder_9
    SRC_ATTRS = sidewalk_area_sqm
    ROUND_TYPE = Nearest
    PLACES = 3
    -> AttributeRemover_13
AttributeRemover_13
    REMOVE_ATTRS = source_id,_overlaps,feat_code,shape_leng,status,sub_code1,_uuid
    -> Extruder_4
Extruder_4
    DISTANCE = 0.1524
    DIRECTION = Auto
    -> ExpressionEvaluator_2
ExpressionEvaluator_2
    ACTION = Create New Attribute
    EXPRESSION = @Value(sidewalk_height_meter)*@Value(sidewalk_area_sqm)
    VAL_ATTR = sidewalk_volume_cubicmeter
    -> AttributeRounder_5
AttributeRounder_5
    SRC_ATTRS = sidewalk_volume_cubicmeter
    ROUND_TYPE = Nearest
    PLACES = 3
    -> Deaggregator_2
Deaggregator_2
    PART_NUMBER_FIELD = _part_number
    GEOM_NAME_FIELD = _geometry_name
    EXPLODE_INSTANCES = No
    LIST_ATTR_MODE_LOOKUP = LEAN
    MODE = Flatten One Level
    SPLIT_COMPOSITES = Yes
    DEAGGREGATED -> GeometryCoercer_2
GeometryCoercer_2
    GQUERY:
      for $geom in //geometry
      where $geom/count(parent::geometry) = 0
      return number($geom/@fme_id)
    KIND = fme_composite_surface
    COERCED -> Deaggregator_3
Deaggregator_3
    PART_NUMBER_FIELD = _part_number
    GEOM_NAME_FIELD = _geometry_name
    EXPLODE_INSTANCES = No
    LIST_ATTR_MODE_LOOKUP = LEAN
    MODE = Flatten One Level
    SPLIT_COMPOSITES = Yes
    DEAGGREGATED -> BoundsExtractor
BoundsExtractor
    XMAX = _xmax
    XMIN = _xmin
    ZMAX = _zmax
    ZMIN = _zmin
    YMIN = _ymin
    YMAX = _ymax
    -> Tester_2
Tester_2
    TEST_CLAUSE:
      TEST @Value(_zmin) = @Value(_zmax)
      TEST @Value(_zmin) != 0
    TEST_MODE = Automatic
    TEST_DESCRIPTION = ""
    BOOL_OP = AND
    PASSED -> Aggregator
    FAILED -> Tester_3
Aggregator
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeCreator_40
AttributeCreator_40
    ATTR_TABLE = SET_TO surfaceType = cover_surface
    -> CityGMLGeometrySetter_3
Tester_3
    TEST_CLAUSE = TEST @Value(_zmax) != 0
    TEST_MODE = Automatic
    TEST_DESCRIPTION = ""
    BOOL_OP = OR
    PASSED -> Aggregator_8
Aggregator_8
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeCreator_41
AttributeCreator_41
    ATTR_TABLE = SET_TO surfaceType = side_surface
    -> CityGMLGeometrySetter_3
CityGMLGeometrySetter_3
    ROLE = trafficArea
    GEOM = lod3MultiSurface
    -> GeometryPropertySetter_6
GeometryPropertySetter_6
    SRC_ATTRS = citygml_lod_name
    OVERWRITE_CHOICE = Yes
    SETTYPE_PARAM = Traits From Attributes
    REMOVE_ATTRIBUTE = No
    SET -> UUIDGenerator_12
UUIDGenerator_12
    UUID_ATTR = _uuid
    -> StringConcatenator_12
StringConcatenator_12
    ACTION = Create New Attribute
    VAL_ATTR = gml_id
    PARM_LINE = @Value(id)@Value(_uuid)
    -> AttributeRemover_2
AttributeRemover_2
    REMOVE_ATTRS = _part_number,id,_xmax,_ymax,_ymin,_zmin,_zmax,_geometry_name,_xmin,_uuid
    -> GeometryColorSetter
GeometryColorSetter
    FILL_COLOR = 0.815686,0.815686,0.815686
    SIDE = Both
    MODE = Fixed
    ALPHA = 1
    COLORED -> ModuloCounter_2
ModuloCounter_2
    MOD = 10
    CNT_ATTR = _modulo_count
    DOMAIN = modcounter
    -> ListPopulator_3
ListPopulator_3
    LIST_NAME = citygml_function
    PREFIX = citygml_function
    -> ListPopulator_4
ListPopulator_4
    LIST_NAME = citygml_usage
    PREFIX = citygml_usage
    -> Road (writer CITYGML_10)
    -> Sidewalk
Sidewalk: Inspector
Road (writer CITYGML_10) [off]
    attributes: _modulo_count xml_char(200), citygml_class xml_buffer, citygml_creationDate xml_date, citygml_feature_role xml_buffer, citygml_function{} xml_buffer, citygml_level_of_detail{0} xml_char(200), citygml_surfaceMaterial xml_char(200), citygml_target_uri xml_buffer, citygml_usage{} xml_buffer, gml_name xml_buffer, sidewalk_adjacent_segmentID xml_char(200), sidewalk_adjacent_street_name xml_char(200), sidewalk_area_sqm xml_char(200), sidewalk_height_inch xml_char(200), sidewalk_height_meter xml_char(200), sidewalk_volume_cubicmeter xml_char(200), surfaceType xml_char(200)

Bookmark: Curbs Manhattan Shape
Curbs_Extract (reader ESRISHAPE_4) [off]
    attributes: sub_code number(33,31), source_id number(33,31), shape_leng number(33,31), status char(254), feat_code number(33,31)
    -> CsmapReprojector_4

Bookmark: Edit Curbs
CsmapReprojector_4
    RASTER_CELL_SIZE = Preserve Cells
    VERTICAL_HANDLING = Ignore heights and leave them unchanged
    DEST = EPSG:32118
    INTERPOLATION_TYPE_NAME = Nearest Neighbor
    REPROJECTED -> Bufferer
Bufferer
    INTERP_SEGMENTS = 8
    OFFSET = 0.2
    CAP_STYLE = Round
    BUFFERED -> Dissolver_4
Dissolver_4
    ACCUM_INPUT_ATTRS = Get Attributes From One Representative Feature
    CONNECT_Z_MODE = First Wins
    NO_OVRLP = No
    AREA -> AttributeRenamer_8
AttributeRenamer_8
    ATTR_TABLE = RENAME_SET_DEFAULT sub_code > sub_code1
    -> AreaOnAreaOverlayer_6 [AREA]
AttributeKeeper_14
    KEEP_ATTRS = externalReference{0}.externalObject.name,road_id,source_id,sidewalk_adjacent_street_name,sidewalk_adjacent_segmentID
    -> AreaOnAreaOverlayer_6 [AREA]
AreaOnAreaOverlayer_6
    CONNECT_Z_MODE = First Wins
    OVC_ATTR = _overlaps
    ACCUM_ATTRS_NAME = Merge Incoming Attributes
    AREA -> Tester_19
Tester_19
    TEST_CLAUSE:
      TEST @Value(_overlaps) = 2
      TEST @Value(sub_code1) = 225000
    TEST_MODE = Automatic
    TEST_DESCRIPTION = ""
    BOOL_OP = AND
    PASSED -> AttributeCreator_20
    FAILED -> Tester_21
AttributeCreator_20
    ATTR_TABLE:
      SET_TO citygml_class = 225000
      SET_TO externalReference{0}.externalObject.name = @Value(source_id)
      SET_TO citygml_function0 = 1220
      SET_TO citygml_surfaceMaterial = 9999
      SET_TO id = id_
      SET_TO externalReference{0}.informationSystem  = https://data.cityofnewyork.us/dataset/Curbs/ikvd-dex8
      SET_TO citygml_target_uri = http://www.opengis.net/citygml/transportation/2.0
      SET_TO curb_height_meter = 0.1524
      SET_TO curb_height_inch = 6
      SET_TO citygml_level_of_detail{0} = 3
      SET_TO gml_parent_id = Road_NYC
      SET_TO gml_name = Kerbstone
    -> UUIDGenerator_5
UUIDGenerator_5
    UUID_ATTR = _uuid
    -> StringConcatenator_5
StringConcatenator_5
    ACTION = Create New Attribute
    VAL_ATTR = gml_id
    PARM_LINE = @Value(id)@Value(_uuid)
    -> AreaCalculator_6
AreaCalculator_6
    AREA_ATTR = _area
    AREA_TYPE = Plane Area
    MULT = 1
    -> AttributeRenamer_9
AttributeRenamer_9
    ATTR_TABLE:
      RENAME_SET_DEFAULT source_id > externalReference{0}.externalObject.name
      RENAME_SET_DEFAULT _area > curb_area_sqm
      RENAME_SET_DEFAULT sidewalk_adjacent_street_name > gml_name
      RENAME_SET_DEFAULT sidewalk_adjacent_segmentID > curb_adjacent_segmentID
    -> AttributeRemover_14
AttributeRemover_14
    REMOVE_ATTRS = _overlaps,feat_code,shape_leng,status,sub_code1,_uuid
    -> Extruder_3
Extruder_3
    DISTANCE = 0.1524
    DIRECTION = Auto
    -> VolumeCalculator
VolumeCalculator
    SET_TRAIT = No
    MULT = 1
    VOLUME_ATTR = curb_volume_cubicmeter
    -> AttributeRounder_4
AttributeRounder_4
    SRC_ATTRS = curb_volume_cubicmeter curb_area_sqm
    ROUND_TYPE = Nearest
    PLACES = 3
    -> Deaggregator_4
Deaggregator_4
    PART_NUMBER_FIELD = _part_number
    GEOM_NAME_FIELD = _geometry_name
    EXPLODE_INSTANCES = No
    LIST_ATTR_MODE_LOOKUP = LEAN
    MODE = Flatten One Level
    SPLIT_COMPOSITES = Yes
    DEAGGREGATED -> GeometryCoercer_3
GeometryCoercer_3
    GQUERY:
      for $geom in //geometry
      where $geom/count(parent::geometry) = 0
      return number($geom/@fme_id)
    KIND = fme_composite_surface
    COERCED -> Deaggregator_5
Deaggregator_5
    PART_NUMBER_FIELD = _part_number
    GEOM_NAME_FIELD = _geometry_name
    EXPLODE_INSTANCES = No
    LIST_ATTR_MODE_LOOKUP = LEAN
    MODE = Flatten One Level
    SPLIT_COMPOSITES = Yes
    DEAGGREGATED -> BoundsExtractor_2
BoundsExtractor_2
    XMAX = _xmax
    XMIN = _xmin
    ZMAX = _zmax
    ZMIN = _zmin
    YMIN = _ymin
    YMAX = _ymax
    -> Tester_4
Tester_4
    TEST_CLAUSE:
      TEST @Value(_zmin) = @Value(_zmax)
      TEST @Value(_zmin) != 0
    TEST_MODE = Automatic
    TEST_DESCRIPTION = ""
    BOOL_OP = AND
    PASSED -> Aggregator_2
    FAILED -> Tester_11
Aggregator_2
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeCreator_38
AttributeCreator_38
    ATTR_TABLE = SET_TO surfaceType = cover_surface
    -> CityGMLGeometrySetter_7
Tester_11
    TEST_CLAUSE = TEST @Value(_zmax) != 0
    TEST_MODE = Automatic
    TEST_DESCRIPTION = ""
    BOOL_OP = OR
    PASSED -> Aggregator_3
Aggregator_3
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeCreator_39
AttributeCreator_39
    ATTR_TABLE = SET_TO surfaceType = side_surface
    -> CityGMLGeometrySetter_7
CityGMLGeometrySetter_7
    ROLE = auxiliaryTrafficArea
    GEOM = lod3MultiSurface
    -> GeometryPropertySetter_3
GeometryPropertySetter_3
    SRC_ATTRS = citygml_lod_name
    OVERWRITE_CHOICE = Yes
    SETTYPE_PARAM = Traits From Attributes
    REMOVE_ATTRIBUTE = No
    SET -> UUIDGenerator_11
UUIDGenerator_11
    UUID_ATTR = _uuid
    -> StringConcatenator_11
StringConcatenator_11
    ACTION = Create New Attribute
    VAL_ATTR = gml_id
    PARM_LINE = @Value(id)@Value(_uuid)
    -> AttributeRemover_3
AttributeRemover_3
    REMOVE_ATTRS = _geometry_name,_ymin,id,_zmax,_xmax,_xmin,_part_number,_uuid,_ymax,_zmin
    -> GeometryColorSetter_4
GeometryColorSetter_4
    FILL_COLOR = 0.301961,0,0
    SIDE = Both
    MODE = Fixed
    ALPHA = 1
    COLORED -> ModuloCounter
ModuloCounter
    MOD = 10
    CNT_ATTR = _modulo_count
    DOMAIN = modcounter
    -> ListPopulator
ListPopulator
    LIST_NAME = citygml_function
    PREFIX = citygml_function
    -> ListPopulator_2
ListPopulator_2
    LIST_NAME = citygml_usage
    PREFIX = citygml_usage
    -> Road (writer CITYGML_11)
    -> Curbs

Bookmark: Parking Lot
Parking_Lots_Extract (reader ESRISHAPE_5) [off]
    attributes: source_id number(33,31), shape_leng number(33,31), shape_area number(33,31), status char(254), sub_code number(33,31), feat_code number(33,31)
    -> CsmapReprojector_5

Bookmark: Edit Parking Lot / Entrance
CsmapReprojector_5
    RASTER_CELL_SIZE = Preserve Cells
    VERTICAL_HANDLING = Ignore heights and leave them unchanged
    DEST = EPSG:32118
    INTERPOLATION_TYPE_NAME = Nearest Neighbor
    REPROJECTED -> AttributeCreator_21
AttributeCreator_21
    ATTR_TABLE = SET_TO citygml_class = 340000
    -> FeatureColorSetter
FeatureColorSetter
    FILL_COLOR = 0.541176,0.541176,0.541176
    COLOR = 0,0,0
    MODE = Fixed
    COLORED -> AreaOnAreaOverlayer_8 [AREA]
AreaOnAreaOverlayer_8
    CONNECT_Z_MODE = First Wins
    OVC_ATTR = _overlaps
    ACCUM_ATTRS_NAME = Merge Incoming Attributes
    AREA -> AttributeKeeper_17
AttributeKeeper_17
    KEEP_ATTRS = externalReference{0}.externalObject.name,road_id,source_id,citygml_class,_overlaps,sidewalk_adjacent_street_name,sidewalk_adjacent_segmentID,sub_code
    -> TestFilter_2
TestFilter_2
    DEFAULT_VALUE = <UNFILTERED>
    TEST_LIST:
      BOOL_OP,AND,COMPOSITE_TEST,<Unused>,TEST_CLAUSE,"TEST @Value(_overlaps) = 1
      TEST @Value(citygml_class) = 340000",Parking Lot,BOOL_OP,AND,COMPOSITE_TEST,<Unused>,TEST_CLAUSE,"TEST @Value(_overlaps) = 2",Entrance,BOOL_OP,AND,COMPOSITE_TEST,<Unused>,TEST_CLAUSE,"TEST @Value(_overlaps) = 1
      TEST @Value(citygml_class) != 340000",Sidewalk
    Parking Lot -> AreaCalculator_7
    Entrance -> AttributeRenamer_10
    Sidewalk -> AttributeKeeper_14
AreaCalculator_7
    AREA_ATTR = parking_lot_area_sqm
    AREA_TYPE = Plane Area
    MULT = 1
    -> Tester_22
Tester_22
    TEST_CLAUSE = TEST @Value(parking_lot_area_sqm) > 50
    TEST_MODE = Automatic
    TEST_DESCRIPTION = ""
    BOOL_OP = OR
    PASSED -> Bufferer_2
Bufferer_2
    INTERP_SEGMENTS = 8
    OFFSET = 0.1
    CAP_STYLE = None
    BUFFERED -> AreaOnAreaOverlayer_7 [AREA]
AttributeRenamer_10
    ATTR_TABLE:
      RENAME_SET_DEFAULT sidewalk_adjacent_segmentID > entrance_adjacent_segmentID
      RENAME_SET_DEFAULT sidewalk_adjacent_street_name > entrance_adjacent_street_name
    -> AreaCalculator_8
    -> AttributeRemover_15
AttributeRemover_15
    REMOVE_ATTRS = citygml_class,sub_code
    -> AreaOnAreaOverlayer_7 [AREA]
AreaOnAreaOverlayer_7
    CONNECT_Z_MODE = First Wins
    LIST_NAME = List
    OVC_ATTR = _overlaps
    ACCUM_ATTRS_NAME = Merge Incoming Attributes
    AREA -> Tester_23
Tester_23
    TEST_CLAUSE = TEST @Value(sub_code) = 500000
    TEST_MODE = Automatic
    TEST_DESCRIPTION = ""
    BOOL_OP = OR
    PASSED -> Dissolver_5
Dissolver_5
    ACCUM_INPUT_ATTRS = Merge Incoming Attributes
    CONNECT_Z_MODE = First Wins
    NO_OVRLP = No
    AREA -> ListDuplicateRemover
ListDuplicateRemover
    SRC_LIST = List{}.entrance_adjacent_street_name
    -> ListConcatenator
ListConcatenator
    LIST_ATTR = List{}.entrance_adjacent_street_name
    SEP = ,
    VAL_ATTR = parking_lot_entrance_street_names
    DROP_EMPTY_PARTS = Yes
    -> Bufferer_4
Bufferer_4
    INTERP_SEGMENTS = 8
    OFFSET = -0.1
    CAP_STYLE = None
    BUFFERED -> AttributeCreator_22
AttributeCreator_22
    ATTR_TABLE:
      SET_TO externalReference{0}.externalObject.name = @Value(source_id)
      SET_TO id = id_
      SET_TO citygml_function{0} = 6
      SET_TO citygml_usage{0} = 2
      SET_TO citygml_target_uri = http://www.opengis.net/citygml/transportation/2.0
      SET_TO externalReference{0}.informationSystem  = https://data.cityofnewyork.us/City-Government/Parking-Lot-Features/h7zy-iq3d/about
      SET_TO citygml_surfaceMaterial = 9999
      SET_TO citygml_creationDate = 2016-12-07
      SET_TO citygml_class = @Value(sub_code)
      SET_TO gml_parent_id = NYC
      SET_TO gml_name = Parking_Lot
      SET_TO externalReference{0}.externalObject.name = @Value(externalReference{0}.externalObject.name)
    -> UUIDGenerator_7
UUIDGenerator_7
    UUID_ATTR = _uuid
    -> StringConcatenator_7
StringConcatenator_7
    ACTION = Create New Attribute
    VAL_ATTR = gml_id
    PARM_LINE = @Value(id)@Value(_uuid)
    -> UUIDGenerator_10
UUIDGenerator_10
    UUID_ATTR = _uuid
    -> StringConcatenator_10
StringConcatenator_10
    ACTION = Create New Attribute
    VAL_ATTR = gml_id
    PARM_LINE = @Value(id)@Value(_uuid)
    -> AttributeRemover_12
AttributeRemover_12
    LIST_ATTRS = List{}._overlaps List{}.citygml_class List{}.entrance_adjacent_street_name List{}.externalReference{} List{}.parking_lot_area_sqm List{}.sidewalk_adjacent_street_name List{}.source_id
    REMOVE_ATTRS = List{0}._overlaps,List{0}.sub_code,_uuid,sidewalk_adjacent_street_name,entrance_adjacent_segmentID,id,sub_code,List{0}.sidewalk_adjacent_street_name,sidewalk_adjacent_segmentID,entrance_adjacent_street_name,List{0}.entrance_adjacent_segmentID,List{0}.source_id,source_id,_overlaps,List{0}.entrance_adjacent_street_name,List{0}.sidewalk_adjacent_segmentID,List{0}.parking_lot_area_sqm,List{0}.citygml_class,road_id
    -> AttributeRounder_8
AttributeRounder_8
    SRC_ATTRS = parking_lot_area_sqm
    ROUND_TYPE = Nearest
    PLACES = 3
    -> Orientor_8
Orientor_8
    KIND = LEFT_HAND_RULE
    ORIENTED -> FaceReplacer_7
FaceReplacer_7
    THICKNESS_TOLERANCE_CHOICE = Automatic
    ANGULAR_TOLERANCE = 0.0
    THICKNESS_TOLERANCE = 0.0
    ANGULAR_TOLERANCE_CHOICE = Automatic
    -> GeometryColorSetter_11
GeometryColorSetter_11
    FILL_COLOR = 0.623529,0.623529,0.623529
    SIDE = Front
    MODE = Fixed
    ALPHA = 1
    COLORED -> Aggregator_15
Aggregator_15
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeRemover_24
AttributeRemover_24
    LIST_ATTRS = List{}.entrance_adjacent_segmentID List{}.road_id List{}.sidewalk_adjacent_segmentID List{}.sub_code
    REMOVE_ATTRS = _part_number,_hierarchy_id,_hierarchy_child_id_list{0},_geometry_name,_hierarchy_parent_id
    -> AttributeCreator_14
AttributeCreator_14
    ATTR_TABLE = SET_TO square_id = square_@Value(gml_id)
    -> AttributeCreator_30
AttributeCreator_30
    ATTR_TABLE = SET_TO gml_parent_id = @Value(square_id)
    -> CityGMLGeometrySetter_12
CityGMLGeometrySetter_12
    ROLE = trafficArea
    GEOM = lod3MultiSurface
    -> GeometryPropertySetter_13
GeometryPropertySetter_13
    SRC_ATTRS = citygml_lod_name
    OVERWRITE_CHOICE = Yes
    SETTYPE_PARAM = Traits From Attributes
    REMOVE_ATTRIBUTE = No
    SET -> Square (writer CITYGML_8)
    SET -> Parking_Lot
Parking_Lot: Inspector
Square (writer CITYGML_8) [off]
    attributes: citygml_class xml_buffer, citygml_creationDate xml_date, citygml_feature_role xml_buffer, citygml_function{0} xml_char(200), citygml_surfaceMaterial xml_char(200), citygml_target_uri xml_buffer, citygml_usage{0} xml_char(200), externalReference{0}.externalObject.name xml_xml, externalReference{0}.informationSystem  xml_xml, gml_name xml_buffer, parking_lot_area_sqm xml_char(200), parking_lot_entrance_street_names xml_char(200), square_id xml_char(200)
AreaCalculator_8
    AREA_ATTR = entrance_area_sqm
    AREA_TYPE = Plane Area
    MULT = 1
    -> AttributeCreator_23
AttributeCreator_23
    ATTR_TABLE:
      SET_TO citygml_class = 380030
      SET_TO id = id_
      SET_TO citygml_target_uri = http://www.opengis.net/citygml/transportation/2.0
      SET_TO externalReference{0}.informationSystem = https://data.cityofnewyork.us/City-Government/Roadbed/xgwd-7vhd/data
      SET_TO externalReference{0}.externalObject.name = @Value(source_id)
      SET_TO citygml_function{0} = 6
      SET_TO citygml_function{1} = 1
      SET_TO citygml_usage{0} = 1
      SET_TO citygml_usage{1} = 2
      SET_TO citygml_surfaceMaterial = 9999
      SET_TO citygml_creationDate = 2016-12-19
      SET_TO gml_parent_id = Road_NYC
      SET_TO gml_name = @Value(entrance_adjacent_street_name)
      SET_TO citygml_function{2} = 2
    -> UUIDGenerator_6
UUIDGenerator_6
    UUID_ATTR = _uuid
    -> StringConcatenator_6
StringConcatenator_6
    ACTION = Create New Attribute
    VAL_ATTR = gml_id
    PARM_LINE = @Value(id)@Value(_uuid)
    -> Orientor_3
Orientor_3
    KIND = LEFT_HAND_RULE
    ORIENTED -> FaceReplacer_5
FaceReplacer_5
    THICKNESS_TOLERANCE_CHOICE = Automatic
    ANGULAR_TOLERANCE = 0.0
    THICKNESS_TOLERANCE = 0.0
    ANGULAR_TOLERANCE_CHOICE = Automatic
    -> GeometryColorSetter_9
GeometryColorSetter_9
    FILL_COLOR = 0.568627,0.568627,0.568627
    SIDE = Front
    MODE = Fixed
    ALPHA = 1
    COLORED -> Aggregator_13
Aggregator_13
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeRemover_22
AttributeRemover_22
    LIST_ATTRS = _hierarchy_child_id_list{}
    REMOVE_ATTRS = source_id,_overlaps,id,_uuid,sub_code
    -> AttributeEncoder
AttributeEncoder
    ATTRCHOICE = Selected Attributes
    DEST_ENCODING = utf-16
    ATTRLIST = externalReference{1}.externalObject.name externalReference{3}.externalObject.name externalReference{0}.externalObject.name externalReference{2}.externalObject.name
    TREAT_AS_BYTES = Honor Encoding
    -> AttributeFilter_2
AttributeFilter_2
    ATTR_VALUES = <EMPTY>,<MISSING>,<NULL>,<UNFILTERED>
    ATTR_NAME = externalReference{0}.externalObject.name
    <MISSING> -> AttributeCreator_16
    <UNFILTERED> -> CityGMLGeometrySetter_13
AttributeCreator_16
    ATTR_TABLE = SET_TO externalReference{0}.externalObject.name = unknown
    -> AttributeEncoder_2
AttributeEncoder_2
    ATTRCHOICE = Selected Attributes
    DEST_ENCODING = utf-16
    ATTRLIST = externalReference{1}.externalObject.name externalReference{3}.externalObject.name externalReference{0}.externalObject.name externalReference{2}.externalObject.name
    TREAT_AS_BYTES = Honor Encoding
    -> CityGMLGeometrySetter_13
CityGMLGeometrySetter_13
    ROLE = trafficArea
    GEOM = lod3MultiSurface
    -> GeometryPropertySetter_14
GeometryPropertySetter_14
    SRC_ATTRS = citygml_lod_name
    OVERWRITE_CHOICE = Yes
    SETTYPE_PARAM = Traits From Attributes
    REMOVE_ATTRIBUTE = No
    SET -> Entrance
Entrance: Inspector

Bookmark: Filtered Centerlines
Road (reader CITYGML_1) [off]
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_function{} xml_buffer, citygml_usage{} xml_buffer, citygml_traffic_area{}.xlink_href xml_buffer, citygml_auxiliary_traffic_area{}.xlink_href xml_buffer, citygml_level_of_detail{} xml_buffer, bike_lane xml_buffer, citygml_class xml_buffer, construction_status xml_buffer, curve_flag xml_buffer, face_code xml_buffer, level_end_segment xml_buffer, level_start_segment xml_buffer, merge_bike_lane xml_buffer, merge_citygml_class xml_buffer, merge_citygml_function xml_buffer, merge_construction_status xml_buffer, merge_curve_flag xml_buffer,
      merge_face_code xml_buffer, merge_gml_name xml_buffer, merge_level_end_segment xml_buffer, merge_level_start_segment xml_buffer, merge_non_pedestrian xml_buffer, merge_physical_id xml_buffer, merge_radius_arc xml_buffer, merge_sanitation_district_boundary_indicator xml_buffer, merge_segment_count xml_buffer, merge_segment_id xml_buffer, merge_segment_type xml_buffer, merge_sequence_number xml_buffer, merge_snow_priority xml_buffer, merge_street_code xml_buffer, merge_traffic_direction xml_buffer, merge_traffic_direction_source xml_buffer, node_id_from xml_buffer, node_id_to xml_buffer, non_pedestrian xml_buffer, number_parking_lanes xml_buffer, number_total_lanes xml_buffer, number_travel_lanes xml_buffer, physical_id xml_buffer, radius_arc xml_buffer, sanitation_district_boundary_indicator xml_buffer, segment_count xml_buffer, segment_id xml_buffer, segment_type xml_buffer, sequence_number xml_buffer, slope_percent xml_buffer,
      snow_priority xml_buffer, special_address_place_name xml_buffer, special_address_place_name_2 xml_buffer, special_address_place_name_3 xml_buffer, special_address_place_name_4 xml_buffer, special_address_place_name_5 xml_buffer, special_address_place_name_6 xml_buffer, special_address_place_name_7 xml_buffer, special_address_place_name_8 xml_buffer, special_address_place_name_9 xml_buffer, special_address_type xml_buffer, special_address_type_2 xml_buffer, special_address_type_3 xml_buffer, special_address_type_4 xml_buffer, special_address_type_5 xml_buffer, special_address_type_6 xml_buffer, special_address_type_7 xml_buffer, special_address_type_8 xml_buffer, special_address_type_9 xml_buffer, street_area_2D_sq_m xml_buffer, street_code xml_buffer, street_length_2D_meter xml_buffer, street_length_3D_meter xml_buffer, street_pavement_rating_date xml_buffer, street_pavement_rating_num xml_buffer, street_pavement_rating_text xml_buffer, street_segment_width_meter xml_buffer, street_speed_limit_km_h xml_buffer, street_speed_limit_mph xml_buffer, street_width_meter xml_buffer,
      traffic_direction xml_buffer, traffic_direction_source xml_buffer
    -> AttributeExposer

Bookmark: Create new Lines and calculate new Length
LineOnAreaOverlayer
    OV_ATTR = _overlaps
    ATTR_ACCUM_MODE = Merge Incoming
    ATTR_CONFLICT_RES = Use Original
    LINE -> LengthCalculator
    LINE -> LineOnAreaOverlayer_3 [LINE]
LengthCalculator
    DIM = 2
    MULT = 1
    LEN_ATTR = _length
    -> Tester_5
Tester_5
    TEST_CLAUSE = TEST @Value(_length) > 18
    TEST_MODE = Automatic
    TEST_DESCRIPTION = ""
    BOOL_OP = OR
    PASSED -> LineJoiner
LineJoiner
    GROUP_BY = gml_name
    TOPOLOGY = End noded
    CONSIDER_NODE_ELEVATION = no
    CONNECT_Z_MODE = First Wins
    PRESERVE = no
    LINES_AS_SEGMENTS = No
    BREAK = no
    ACCUM_ATTRS_NAME = Get Attributes From One Representative Feature
    LINE -> LengthCalculator_6
LengthCalculator_6
    DIM = 2
    MULT = 1
    LEN_ATTR = _length
    -> AttributeCreator_7
AttributeCreator_7
    ATTR_TABLE = SET_TO street_length_3D_meter = @Value(_length)
    -> LineOnAreaOverlayer_2 [LINE]

Bookmark: Match Roadbed to new Centerlines if ratio = 1:1
LineOnAreaOverlayer_2
    OV_ATTR = _overlaps
    ATTR_ACCUM_MODE = Merge Incoming
    ATTR_CONFLICT_RES = Use Original
    AREA -> Tester_6
Tester_6
    TEST_CLAUSE = TEST @Value(_overlaps) = 1
    TEST_MODE = Automatic
    TEST_DESCRIPTION = ""
    BOOL_OP = OR
    PASSED -> LineOnAreaOverlayer_6 [AREA]
    PASSED -> LineOnAreaOverlayer_3 [AREA]
    PASSED -> CityGMLGeometrySetter_2
    FAILED -> AreaOnAreaOverlayer [AREA]

Bookmark: Select remaining Centerlines, join and calculate new length
LineOnAreaOverlayer_3
    OV_ATTR = _overlaps
    ATTR_ACCUM_MODE = Merge Incoming
    ATTR_CONFLICT_RES = Use Original
    LINE -> Tester_7
Tester_7
    TEST_CLAUSE = TEST @Value(_overlaps) = 0
    TEST_MODE = Automatic
    TEST_DESCRIPTION = ""
    BOOL_OP = OR
    PASSED -> LineJoiner_2
LineJoiner_2
    GROUP_BY = gml_name
    TOPOLOGY = End noded
    CONSIDER_NODE_ELEVATION = no
    CONNECT_Z_MODE = First Wins
    PRESERVE = no
    LINES_AS_SEGMENTS = No
    BREAK = no
    ACCUM_ATTRS_NAME = Get Attributes From One Representative Feature
    LINE -> LengthCalculator_3
LengthCalculator_3
    DIM = 2
    MULT = 1
    LEN_ATTR = _length
    -> Tester_8
Tester_8
    TEST_CLAUSE = TEST @Value(_length) > 25
    TEST_MODE = Automatic
    TEST_DESCRIPTION = ""
    BOOL_OP = OR
    PASSED -> AttributeCreator_4
AttributeCreator_4
    ATTR_TABLE = SET_TO street_length_3D_meter = @Value(_length)
    -> LineOnAreaOverlayer_4 [LINE]

Bookmark: Self-intersect remining Roadbed geometries and create new Centerlines
AreaOnAreaOverlayer
    CONNECT_Z_MODE = First Wins
    OVC_ATTR = _overlaps
    ACCUM_ATTRS_NAME = Get Attributes From One Representative Feature
    AREA -> AttributeKeeper_7
    AREA -> AttributeKeeper_8
AttributeKeeper_7
    -> LineOnAreaOverlayer_4 [AREA]
LineOnAreaOverlayer_4
    OV_ATTR = _overlaps
    ATTR_ACCUM_MODE = Merge Incoming
    ATTR_CONFLICT_RES = Use Original
    LINE -> LengthCalculator_4
LengthCalculator_4
    DIM = 2
    MULT = 1
    LEN_ATTR = _length
    -> Tester_9
Tester_9
    TEST_CLAUSE = TEST @Value(_length) > 25
    TEST_MODE = Automatic
    TEST_DESCRIPTION = ""
    BOOL_OP = OR
    PASSED -> LineOnAreaOverlayer_5 [LINE]
    PASSED -> LineOnAreaOverlayer_6 [LINE]

Bookmark: Match new Roadbed Geometries with new Centerlines if ratio = 1:1
AttributeKeeper_8
    -> LineOnAreaOverlayer_5 [AREA]
LineOnAreaOverlayer_5
    OV_ATTR = _overlaps
    ATTR_ACCUM_MODE = Merge Incoming
    ATTR_CONFLICT_RES = Use Original
    AREA -> Tester_10
Tester_10
    TEST_CLAUSE = TEST @Value(_overlaps) = 1
    TEST_MODE = Automatic
    TEST_DESCRIPTION = ""
    BOOL_OP = OR
    PASSED -> CityGMLGeometrySetter_2
    PASSED -> LineOnAreaOverlayer_6 [AREA]
    FAILED -> Chopper

Bookmark: Select unmatched Centerlines / Chop unmatched areas
LineOnAreaOverlayer_6
    OV_ATTR = _overlaps
    ATTR_ACCUM_MODE = Merge Incoming
    ATTR_CONFLICT_RES = Use Original
    LINE -> NeighborFinder [CANDIDATE]
Chopper
    MAX_VERTICES = 7
    REMNANT_ATTR = _remnant
    CHOPPED_ATTR = _chopped
    MODE = By Vertex
    -> AttributeKeeper_22
AttributeKeeper_22
    KEEP_ATTRS = sub_code
    -> NeighborFinder [BASE]
NeighborFinder
    ATTR_ACCUM_MODE = Merge Candidate
    TREAT_POLYGON_AS = Areas
    CANDIDATES_FIRST = No
    K = 1
    MAX = 25
    ATTR_CONFLICT_RES = Use Base
    MODE = Bases and Candidates
    INSERT_VERTEX = No
    MATCHED -> Dissolver_6
Dissolver_6
    GROUP_BY = segment_id gml_name
    ACCUM_INPUT_ATTRS = Merge Incoming Attributes
    CONNECT_Z_MODE = First Wins
    NO_OVRLP = No
    AREA -> AttributeCreator_5
AttributeCreator_5
    ATTR_TABLE = SET_TO orientation = 1
    -> CityGMLGeometrySetter_2

Bookmark: Roadbed Post-Processing
CityGMLGeometrySetter_2
    ROLE = trafficArea
    GEOM = lod3MultiSurface
    -> AreaCalculator
AreaCalculator
    AREA_ATTR = _area
    AREA_TYPE = Plane Area
    MULT = 1
    -> AttributeRounder_2
AttributeRounder_2
    SRC_ATTRS = street_width_meter street_length_2D_meter street_segment_width_meter street_length_3D_meter _area _length street_area_2D_sq_m
    ROUND_TYPE = Nearest
    PLACES = 3
    -> AttributeCreator_8
AttributeCreator_8
    ATTR_TABLE = SET_TO id = id_
    -> UUIDGenerator
UUIDGenerator
    UUID_ATTR = _uuid
    -> StringConcatenator
StringConcatenator
    ACTION = Create New Attribute
    VAL_ATTR = _result
    PARM_LINE = @Value(id)@Value(_uuid)
    -> AttributeCreator_6
AttributeCreator_6
    ATTR_TABLE:
      SET_TO street_area_3D_sqm = @Value(_area)
      SET_TO citygml_level_of_detail{0} = 3
      SET_TO street_length_3D_meter = @Value(street_length_3D_meter)
      SET_TO citygml_usage{0} = 2
      SET_TO citygml_class = @Value(sub_code)
      SET_TO gml_id = @Value(_result)
      SET_TO citygml_creationDate = 2016-11-28
      SET_TO street_width_meter = @Evaluate(@Value(street_area_2D_sq_m)/@Value(street_length_3D_meter))
      SET_TO citygml_function{0} = 1
      SET_TO citygml_level_of_detail{0} = 3
      SET_TO citygml_surfaceMaterial = 9999
      SET_TO road_id = road_@Value(gml_id)
    -> AttributeKeeper_9
AttributeKeeper_9
    KEEP_ATTRS = externalReference{1}.externalObject.name,orientation,citygml_class,street_code,externalReference{0}.informationSystem,gml_parent_id,segment_type,special_address_place_name_3,construction_status,street_pavement_rating_num,externalReference{0}.externalObject.name,citygml_creationDate,radius_arc,face_code,citygml_feature_role_attr_val,snow_priority,externalReference{1}.externalObject.uri,citygml_surfaceMaterial,slope_percent,citygml_target_uri,special_address_place_name_2,traffic_direction_source,curve_flag,segment_count,externalReference{0}.externalObject.uri,street_width_meter,node_id_to,sanitation_district_boundary_indicator,special_address_type,citygml_lod_name,street_length_3D_meter,citygml_generalizes_to{0}.xlink_href,road_id,externalReference{1}.informationSystem,number_parking_lanes,street_pavement_rating_text,traffic_direction,bike_lane,gml_id,street_area_3D_sqm,street_speed_limit_km_h,special_address_place_name_4,street_speed_limit_mph,level_end_segment,citygml_auxiliary_traffic_area{0}.xlink_href,special_address_place_name_5,gml_description,number_travel_lanes,number_total_lanes,citygml_traffic_area{0}.xlink_href,citygml_terminationDate,street_pavement_rating_date,physical_id,sequence_number,special_address_type_4,segment_id,special_address_type_3,citygml_level_of_detail{0},externalReference{2}.externalObject.name,node_id_from,externalReference{2}.externalObject.uri,citygml_feature_role,special_address_type_2,status,special_address_type_5,citygml_function{0},special_address_place_name,level_start_segment,citygml_feature_role_attr_name,gml_name,citygml_usage{0},externalReference{2}.informationSystem
    KEEP_LIST = citygml_appearance{}.xlink_href citygml_auxiliary_traffic_area{} citygml_function{} citygml_generalizes_to{}.xlink_href citygml_level_of_detail{} citygml_traffic_area{} citygml_usage{} externalReference{}.externalObject.name externalReference{}.externalObject.uri externalReference{}.informationSystem
    -> AreaOnAreaOverlayer_2 [AREA]

Bookmark: Cut Median from Roadbed Geometries
AreaOnAreaOverlayer_2
    CONNECT_Z_MODE = First Wins
    OVC_ATTR = _overlaps
    ACCUM_ATTRS_NAME = Merge Incoming Attributes
    AREA -> Tester_14
Tester_14
    TEST_CLAUSE = TEST @Value(feat_code) = 3600
    TEST_MODE = Automatic
    TEST_DESCRIPTION = ""
    BOOL_OP = OR
    PASSED -> Tester_13
    FAILED -> Dissolver_7
Dissolver_7
    GROUP_BY = segment_id
    ACCUM_INPUT_ATTRS = Merge Incoming Attributes
    CONNECT_Z_MODE = First Wins
    NO_OVRLP = No
    AREA -> FeatureColorSetter_2
FeatureColorSetter_2
    FILL_COLOR = 0.619608,0.619608,0.619608
    COLOR = 0,0,0
    MODE = Fixed
    COLORED -> AttributeRemover_4
AttributeRemover_4
    REMOVE_ATTRS = shape_area,source_id,sub_code,_overlaps,feat_code,shape_leng
    -> AttributeCreator
AttributeCreator
    ATTR_TABLE:
      SET_TO id = id_
      SET_TO citygml_target_uri = http://www.opengis.net/citygml/transportation/2.0
      SET_TO citygml_class = 350000
    -> UUIDGenerator_18
UUIDGenerator_18
    UUID_ATTR = _uuid
    -> StringConcatenator_18
StringConcatenator_18
    ACTION = Create New Attribute
    VAL_ATTR = gml_id
    PARM_LINE = @Value(id)@Value(_uuid)
    -> AttributeRemover_16
AttributeRemover_16
    REMOVE_ATTRS = _uuid,status,street_nam,id
    -> GeometryPropertySetter_2
    -> NeighborFinder_3 [CANDIDATE]
GeometryPropertySetter_2
    SRC_ATTRS = citygml_lod_name
    OVERWRITE_CHOICE = Yes
    SETTYPE_PARAM = Traits From Attributes
    REMOVE_ATTRIBUTE = No
    SET -> Orientor_2
Orientor_2
    KIND = LEFT_HAND_RULE
    ORIENTED -> FaceReplacer_3
FaceReplacer_3
    THICKNESS_TOLERANCE_CHOICE = Automatic
    ANGULAR_TOLERANCE = 0.0
    THICKNESS_TOLERANCE = 0.0
    ANGULAR_TOLERANCE_CHOICE = Automatic
    -> GeometryColorSetter_7
GeometryColorSetter_7
    FILL_COLOR = 0.576471,0.576471,0.576471
    SIDE = Front
    MODE = Fixed
    ALPHA = 1
    COLORED -> Aggregator_11
Aggregator_11
    AGGREGATE_TYPE = Homogeneous Collection (If Possible)
    ORDERED = No
    SEP = ,
    GROUP_BY = gml_id
    MODE = Geometry - Assemble One Level
    ACCUM_ATTRS_NAME = Get Attributes From One Representative Feature
    AGGREGATE -> CityGMLGeometrySetter_8
    AGGREGATE -> AttributeKeeper_2
CityGMLGeometrySetter_8
    ROLE = trafficArea
    GEOM = lod3MultiSurface
    -> GeometryPropertySetter_5
GeometryPropertySetter_5
    SRC_ATTRS = citygml_lod_name
    OVERWRITE_CHOICE = Yes
    SETTYPE_PARAM = Traits From Attributes
    REMOVE_ATTRIBUTE = No
    SET -> AttributeFilter_3
AttributeFilter_3
    ATTR_VALUES = <EMPTY>,<MISSING>,<NULL>,<UNFILTERED>
    ATTR_NAME = externalReference{1}.externalObject.name
    <MISSING> -> Roadbed
    <MISSING> -> Road (writer CITYGML_2)
    <UNFILTERED> -> AttributeCreator_3
AttributeCreator_3
    ATTR_TABLE = SET_TO externalReference{1}.informationSystem = https://data.cityofnewyork.us/Transportation/Street-Pavement-Rating/2cav-chmn/data
    -> Roadbed
    -> Road (writer CITYGML_2)

Bookmark: Edit Median on Street
Tester_13
    TEST_CLAUSE = TEST @Value(_overlaps) > 1
    TEST_MODE = Automatic
    TEST_DESCRIPTION = ""
    BOOL_OP = OR
    PASSED -> AreaCalculator_2
    FAILED -> AreaOnAreaOverlayer_3 [AREA]
AreaCalculator_2
    AREA_ATTR = _area
    AREA_TYPE = Plane Area
    MULT = 1
    -> LengthCalculator_5
LengthCalculator_5
    DIM = 2
    MULT = 1
    LEN_ATTR = _length
    -> AttributeCreator_9
AttributeCreator_9
    ATTR_TABLE:
      SET_TO median_area_sqm = @Value(_area)
      SET_TO median_perimeter_meter = @Value(_length)
      SET_TO citygml_class = @Value(sub_code)
      SET_TO citygml_creationDate = 2016-11-29
      SET_TO id = id_
      SET_TO citygml_function{0} = 14
      SET_TO gml_name = @Value(gml_name)
      SET_TO gml_parent_id = @Value(road_id)
    -> AttributeRounder_7
AttributeRounder_7
    SRC_ATTRS = median_perimeter_meter _area _length median_area_sqm
    ROUND_TYPE = Nearest
    PLACES = 3
    -> UUIDGenerator_2
UUIDGenerator_2
    UUID_ATTR = _uuid
    -> StringConcatenator_2
StringConcatenator_2
    ACTION = Create New Attribute
    VAL_ATTR = _result
    PARM_LINE = @Value(id)@Value(_uuid)
    -> AttributeKeeper_10
AttributeKeeper_10
    KEEP_ATTRS = gml_parent_id,citygml_creationDate,citygml_target_uri,road_id,citygml_class,source_id,gml_id,median_area_sqm,gml_name
    -> Dissolver

Bookmark: Median not on Street
AreaOnAreaOverlayer_3
    CONNECT_Z_MODE = First Wins
    OVC_ATTR = _overlaps
    ACCUM_ATTRS_NAME = Get Attributes From One Representative Feature
    AREA -> Tester_16
Tester_16
    TEST_CLAUSE = TEST @Value(_overlaps) = 1
    TEST_MODE = Automatic
    TEST_DESCRIPTION = ""
    BOOL_OP = OR
    PASSED -> AreaCalculator_3
AreaCalculator_3
    AREA_ATTR = _area
    AREA_TYPE = Plane Area
    MULT = 1
    -> LengthCalculator_7
LengthCalculator_7
    DIM = 2
    MULT = 1
    LEN_ATTR = _length
    -> AttributeRounder
AttributeRounder
    SRC_ATTRS = _area _length
    ROUND_TYPE = Nearest
    PLACES = 3
    -> AttributeCreator_10
AttributeCreator_10
    ATTR_TABLE:
      SET_TO citygml_class = @Value(sub_code)
      SET_TO citygml_creationDate = 2016-11-29
      SET_TO median_area_sqm = @Value(_area)
      SET_TO median_perimeter_meter = @Value(_length)
      SET_TO id = id_
    -> UUIDGenerator_3
UUIDGenerator_3
    UUID_ATTR = _uuid
    -> StringConcatenator_3
StringConcatenator_3
    ACTION = Create New Attribute
    VAL_ATTR = gml_id
    PARM_LINE = @Value(id)@Value(_uuid)
    -> TestFilter_3
TestFilter_3
    DEFAULT_VALUE = <UNFILTERED>
    TEST_LIST = BOOL_OP,OR,COMPOSITE_TEST,<Unused>,TEST_CLAUSE,"TEST @Value(sub_code) = 360010",Median_Painted,BOOL_OP,OR,COMPOSITE_TEST,<Unused>,TEST_CLAUSE,"TEST @Value(sub_code) = 360020",Median_Curb,BOOL_OP,OR,COMPOSITE_TEST,<Unused>,TEST_CLAUSE,"TEST @Value(sub_code) = 360030",Median_Rail,BOOL_OP,OR,COMPOSITE_TEST,<Unused>,TEST_CLAUSE,"TEST @Value(sub_code) = 360040",Median_Fence,BOOL_OP,OR,COMPOSITE_TEST,<Unused>,TEST_CLAUSE,"TEST @Value(sub_code) = 360050",Median_Grass,BOOL_OP,OR,COMPOSITE_TEST,<Unused>,TEST_CLAUSE,"TEST @Value(sub_code) = 360060",Median_Barrier
    Median_Painted -> Dissolver
    Median_Curb -> AttributeCreator_12
    Median_Grass -> AttributeCreator_15
Dissolver
    GROUP_BY = source_id
    ACCUM_INPUT_ATTRS = Merge Incoming Attributes
    CONNECT_Z_MODE = First Wins
    NO_OVRLP = No
    AREA -> AreaOnAreaOverlayer_5 [AREA]
AreaOnAreaOverlayer_5
    CONNECT_Z_MODE = First Wins
    OVC_ATTR = _overlaps
    ACCUM_ATTRS_NAME = Get Attributes From One Representative Feature
    AREA -> Tester_18
Tester_18
    TEST_CLAUSE:
      TEST @Value(_overlaps) = 1
      TEST @Value(citygml_class) = 360010
    TEST_MODE = Automatic
    TEST_DESCRIPTION = ""
    BOOL_OP = AND
    PASSED -> AttributeCreator_11
AttributeCreator_11
    ATTR_TABLE:
      SET_TO citygml_surfaceMaterial = 9999
      SET_TO externalReference{0}.informationSystem = https://data.cityofnewyork.us/Transportation/Median/27b5-th78/data
      SET_TO externalReference{0}.externalObject.name = @Value(source_id)
      SET_TO gml_parent_id = @Value(road_id)
      SET_TO citygml_function{0} = 11
      SET_TO citygml_class = 360010
      SET_TO id = id_
      SET_TO citygml_target_uri = http://www.opengis.net/citygml/transportation/2.0
    -> UUIDGenerator_17
UUIDGenerator_17
    UUID_ATTR = _uuid
    -> StringConcatenator_17
StringConcatenator_17
    ACTION = Create New Attribute
    VAL_ATTR = gml_id
    PARM_LINE = @Value(id)@Value(_uuid)
    -> Orientor
Orientor
    KIND = LEFT_HAND_RULE
    ORIENTED -> AttributeRemover_7
AttributeRemover_7
    REMOVE_ATTRS = id,shape_area,_length,source_id,street_nam,sub_code,_overlaps,feat_code,shape_leng,status,_area,_uuid
    -> AttributeKeeper_15
AttributeKeeper_15
    KEEP_ATTRS = gml_parent_id,citygml_feature_role_attr_name,curve_flag,citygml_lod_name,road_id,citygml_usage{0},citygml_creationDate,citygml_target_uri,gml_id,externalReference{0}.informationSystem,face_code,citygml_feature_role_attr_val,citygml_terminationDate,externalReference{0}.externalObject.name,citygml_function{0},gml_name,citygml_feature_role,median_area_sqm,citygml_class,citygml_level_of_detail{0},citygml_surfaceMaterial
    -> FaceReplacer
FaceReplacer
    THICKNESS_TOLERANCE_CHOICE = Automatic
    ANGULAR_TOLERANCE = 0.0
    THICKNESS_TOLERANCE = 0.0
    ANGULAR_TOLERANCE_CHOICE = Automatic
    -> GeometryColorSetter_5
GeometryColorSetter_5
    FILL_COLOR = 1,1,1
    SIDE = Front
    MODE = Fixed
    ALPHA = 1
    COLORED -> Aggregator_9
Aggregator_9
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeRemover_18
AttributeRemover_18
    LIST_ATTRS = _hierarchy_child_id_list{}
    REMOVE_ATTRS = _part_number,_hierarchy_id,_hierarchy_child_id_list{0},_geometry_name,_hierarchy_parent_id
    -> CityGMLGeometrySetter_4
CityGMLGeometrySetter_4
    ROLE = auxiliaryTrafficArea
    GEOM = lod3MultiSurface
    -> GeometryPropertySetter_7
GeometryPropertySetter_7
    SRC_ATTRS = citygml_lod_name
    OVERWRITE_CHOICE = Yes
    SETTYPE_PARAM = Traits From Attributes
    REMOVE_ATTRIBUTE = No
    SET -> Median_Painted
    SET -> Road (writer CITYGML_4)
    SET -> AttributeKeeper_20
AttributeKeeper_20
    KEEP_ATTRS = gml_parent_id,road_id,gml_name
    -> NeighborFinder_5 [CANDIDATE]
AttributeCreator_12
    ATTR_TABLE:
      SET_TO citygml_surfaceMaterial = 9999
      SET_TO externalReference{0}.informationSystem = https://data.cityofnewyork.us/Transportation/Median/27b5-th78/data
      SET_TO externalReference{0}.externalObject.name = @Value(source_id)
      SET_TO median_height_inch = 12
      SET_TO median_height_meter = 0.3048
      SET_TO citygml_function{0} = 1300
      SET_TO id_ = id_
      SET_TO gml_name = @Value(gml_name)
      SET_TO citygml_target_uri = http://www.opengis.net/citygml/transportation/2.0
    -> AttributeRemover_6
AttributeRemover_6
    REMOVE_ATTRS = source_id,shape_leng,shape_area,id,_area,feat_code,_uuid,_length,sub_code,_overlaps,status,street_nam
    -> Extruder_2
Extruder_2
    DISTANCE = 0.3048
    DIRECTION = Auto
    -> AttributeKeeper_16
AttributeKeeper_16
    KEEP_ATTRS = citygml_function{0},id_,citygml_feature_role_attr_name,externalReference{0}.externalObject.name,citygml_lod_name,median_area_sqm,gml_name,gml_parent_id,citygml_feature_role_attr_val,median_height_inch,citygml_class,gml_id,citygml_target_uri,citygml_feature_role,citygml_surfaceMaterial,citygml_terminationDate,externalReference{0}.informationSystem,citygml_creationDate,median_height_meter,citygml_level_of_detail{0}
    -> VolumeCalculator_3
VolumeCalculator_3
    SET_TRAIT = No
    MULT = 1
    VOLUME_ATTR = median_volume_cubicmeter
    -> AttributeRounder_3
AttributeRounder_3
    SRC_ATTRS = median_area_sqm median_volume_cubicmeter
    ROUND_TYPE = Nearest
    PLACES = 3
    -> Deaggregator_8
Deaggregator_8
    PART_NUMBER_FIELD = _part_number
    GEOM_NAME_FIELD = _geometry_name
    EXPLODE_INSTANCES = No
    LIST_ATTR_MODE_LOOKUP = LEAN
    MODE = Flatten One Level
    SPLIT_COMPOSITES = Yes
    DEAGGREGATED -> GeometryCoercer_5
GeometryCoercer_5
    GQUERY:
      for $geom in //geometry
      where $geom/count(parent::geometry) = 0
      return number($geom/@fme_id)
    KIND = fme_composite_surface
    COERCED -> Deaggregator_9
Deaggregator_9
    PART_NUMBER_FIELD = _part_number
    GEOM_NAME_FIELD = _geometry_name
    EXPLODE_INSTANCES = No
    LIST_ATTR_MODE_LOOKUP = LEAN
    MODE = Flatten One Level
    SPLIT_COMPOSITES = Yes
    DEAGGREGATED -> BoundsExtractor_4
BoundsExtractor_4
    XMAX = _xmax
    XMIN = _xmin
    ZMAX = _zmax
    ZMIN = _zmin
    YMIN = _ymin
    YMAX = _ymax
    -> Tester_26
Tester_26
    TEST_CLAUSE:
      TEST @Value(_zmin) = @Value(_zmax)
      TEST @Value(_zmin) != 0
    TEST_MODE = Automatic
    TEST_DESCRIPTION = ""
    BOOL_OP = AND
    PASSED -> Aggregator_6
    FAILED -> Tester_27
Aggregator_6
    AGGREGATE_TYPE = Homogeneous Collection (If Possible)
    ORDERED = No
    SEP = ,
    GROUP_BY = gml_id
    MODE = Geometry - Assemble One Level
    ACCUM_ATTRS_NAME = Get Attributes From One Representative Feature
    AGGREGATE -> UUIDGenerator_13
Tester_27
    TEST_CLAUSE = TEST @Value(_zmax) != 0
    TEST_MODE = Automatic
    TEST_DESCRIPTION = ""
    BOOL_OP = OR
    PASSED -> Aggregator_7
Aggregator_7
    AGGREGATE_TYPE = Homogeneous Collection (If Possible)
    ORDERED = No
    SEP = ,
    GROUP_BY = gml_id
    MODE = Geometry - Assemble One Level
    ACCUM_ATTRS_NAME = Get Attributes From One Representative Feature
    AGGREGATE -> UUIDGenerator_13
UUIDGenerator_13
    UUID_ATTR = _uuid
    -> StringConcatenator_13
StringConcatenator_13
    ACTION = Create New Attribute
    VAL_ATTR = gml_id
    PARM_LINE = @Value(id_)@Value(_uuid)
    -> NeighborFinder_4 [BASE]
NeighborFinder_4
    ATTR_ACCUM_MODE = Merge Candidate
    TREAT_POLYGON_AS = Areas
    CANDIDATES_FIRST = No
    K = 1
    MAX = 5
    ATTR_CONFLICT_RES = Use Base
    MODE = Bases and Candidates
    INSERT_VERTEX = No
    MATCHED -> AttributeCreator_27
AttributeCreator_27
    ATTR_TABLE = SET_TO gml_parent_id = @Value(road_id)
    -> AttributeRemover_9
AttributeRemover_9
    REMOVE_ATTRS = id_,_xmin,_distance,_closest_candidate_y,_closest_candidate_x,_xmax,_zmin,_ymax,_angle,_candidate_angle,_candidate_label_angle,_uuid,_geometry_name,_zmax,_closest_base_y,_part_number,_ymin,_closest_base_x
    -> CityGMLGeometrySetter_5
CityGMLGeometrySetter_5
    ROLE = auxiliaryTrafficArea
    GEOM = lod3MultiSurface
    -> GeometryPropertySetter
GeometryPropertySetter
    SRC_ATTRS = citygml_lod_name
    OVERWRITE_CHOICE = Yes
    SETTYPE_PARAM = Traits From Attributes
    REMOVE_ATTRIBUTE = No
    SET -> GeometryColorSetter_3
GeometryColorSetter_3
    FILL_COLOR = 0.666667,0.333333,0
    SIDE = Both
    MODE = Fixed
    ALPHA = 1
    COLORED -> Road (writer CITYGML_5)
    COLORED -> Median_Raised
AttributeCreator_15
    ATTR_TABLE:
      SET_TO citygml_surfaceMaterial = 10
      SET_TO externalReference{0}.informationSystem = https://data.cityofnewyork.us/Transportation/Median/27b5-th78/data
      SET_TO externalReference{0}.externalObject.name = @Value(source_id)
      SET_TO median_height_inch = 0
      SET_TO median_height_meter = 0
      SET_TO citygml_function{0} = 1020
      SET_TO id_ = id_
      SET_TO citygml_function{0} = 1020
      SET_TO citygml_target_uri = http://www.opengis.net/citygml/transportation/2.0
    -> StringConcatenator_14
StringConcatenator_14
    ACTION = Create New Attribute
    VAL_ATTR = gml_id
    PARM_LINE = @Value(id_)@Value(_uuid)
    -> UUIDGenerator_14
UUIDGenerator_14
    UUID_ATTR = _uuid
    -> AttributeRemover_8
AttributeRemover_8
    REMOVE_ATTRS = id,id_,shape_area,_length,source_id,street_nam,sub_code,_overlaps,feat_code,shape_leng,status,_area,_uuid
    -> AttributeKeeper_21
AttributeKeeper_21
    KEEP_ATTRS = citygml_feature_role_attr_name,externalReference{0}.externalObject.name,citygml_lod_name,median_area_sqm,gml_name,gml_parent_id,citygml_feature_role_attr_val,road_id,median_height_inch,citygml_class,gml_id,citygml_target_uri,citygml_feature_role,citygml_surfaceMaterial,citygml_terminationDate,externalReference{0}.informationSystem,citygml_creationDate,median_height_meter,citygml_level_of_detail{0}
    -> Orientor_6
Orientor_6
    KIND = LEFT_HAND_RULE
    ORIENTED -> FaceReplacer_2
FaceReplacer_2
    THICKNESS_TOLERANCE_CHOICE = Automatic
    ANGULAR_TOLERANCE = 0.0
    THICKNESS_TOLERANCE = 0.0
    ANGULAR_TOLERANCE_CHOICE = Automatic
    -> GeometryColorSetter_6
GeometryColorSetter_6
    FILL_COLOR = 0.333333,0.666667,0
    SIDE = Front
    MODE = Fixed
    ALPHA = 1
    COLORED -> Aggregator_10
Aggregator_10
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeRemover_19
AttributeRemover_19
    LIST_ATTRS = _hierarchy_child_id_list{}
    REMOVE_ATTRS = _part_number,_hierarchy_id,_hierarchy_child_id_list{0},_geometry_name,_hierarchy_parent_id
    -> NeighborFinder_5 [BASE]
NeighborFinder_5
    ATTR_ACCUM_MODE = Merge Candidate
    TREAT_POLYGON_AS = Areas
    CANDIDATES_FIRST = No
    K = 1
    ATTR_CONFLICT_RES = Use Base
    MODE = Bases and Candidates
    INSERT_VERTEX = No
    MATCHED -> CityGMLGeometrySetter_6
CityGMLGeometrySetter_6
    ROLE = auxiliaryTrafficArea
    GEOM = lod3MultiSurface
    -> GeometryPropertySetter_10
GeometryPropertySetter_10
    SRC_ATTRS = citygml_lod_name
    OVERWRITE_CHOICE = Yes
    SETTYPE_PARAM = Traits From Attributes
    REMOVE_ATTRIBUTE = No
    SET -> Road (writer CITYGML_6)
    SET -> Grass

Bookmark: Intersections
LineOnAreaOverlayer_7
    OV_ATTR = _overlaps
    ATTR_ACCUM_MODE = Merge Incoming
    LIST_NAME = Intersection_List
    ATTR_CONFLICT_RES = Use Original
    AREA -> AttributeKeeper
AttributeKeeper
    KEEP_ATTRS = special_address_type_5,construction_status,special_address_place_name,snow_priority,gml_parent_id,citygml_class_codeSpace,citygml_usage{0}.codeSpace,gml_description,special_address_place_name_5,special_address_place_name_2,citygml_feature_role_attr_name,citygml_auxiliary_traffic_area{0}.xlink_href,special_address_type_3,special_address_place_name_4,special_address_type_2,citygml_creationDate,citygml_function{0}.codeSpace,citygml_feature_role_attr_val,externalReference{0}.informationSystem,citygml_relative_to_water,citygml_feature_role,sanitation_district_boundary_indicator,citygml_traffic_area{0}.xlink_href,citygml_generalizes_to{0}.xlink_href,citygml_terminationDate,special_address_place_name_3,citygml_level_of_detail{0},citygml_target_uri,externalReference{0}.externalObject.uri,special_address_type,citygml_class,special_address_type_4,source_id,externalReference{0}.externalObject.name,sub_code,citygml_relative_to_terrain
    KEEP_LIST = Intersection_List{}.gml_name Intersection_List{}.segment_id
    -> AttributeCreator_2
AttributeCreator_2
    ATTR_TABLE:
      SET_TO externalReference{0}.externalObject.name = @Value(source_id)
      SET_TO externalReference{0}.informationSystem = https://data.cityofnewyork.us/City-Government/Roadbed/xgwd-7vhd/data
      SET_TO id = id_
      SET_TO citygml_surfaceMaterial = 9999
      SET_TO citygml_function{0} = 1
      SET_TO citygml_usage{0} = 2
      SET_TO citygml_creationDate = 2016-12-08
      SET_TO gml_parent_id = Road_NYC
      SET_TO citygml_level_of_detail{0} = 3
      SET_TO citygml_class = 350010
      SET_TO gml_name = Intersection
      SET_TO citygml_target_uri = http://www.opengis.net/citygml/transportation/2.0
    -> ListElementCounter
ListElementCounter
    LIST_NAME = Intersection_List{}
    CNT_ATTR = intersecting_segements_count
    -> ListCopier
ListCopier
    SRC_LIST = Intersection_List{}
    DEST_LIST = intersecting_street_names
    -> ListDuplicateRemover_2
ListDuplicateRemover_2
    SRC_LIST = intersecting_street_names{}.gml_name
    -> ListConcatenator_2
ListConcatenator_2
    LIST_ATTR = Intersection_List{}.segment_id
    SEP = ,
    VAL_ATTR = intersecting_segmentIDs_conc
    DROP_EMPTY_PARTS = Yes
    -> ListConcatenator_3
ListConcatenator_3
    LIST_ATTR = intersecting_street_names{}.gml_name
    SEP = ,
    VAL_ATTR = intersecting_street_names_conc
    DROP_EMPTY_PARTS = Yes
    -> AttributeRemover_11
AttributeRemover_11
    LIST_ATTRS = Intersection_List{}.gml_name intersecting_street_names{}.segment_id
    -> ListRenamer
ListRenamer
    LIST_COMPONENT_NAMES = Intersection_List{},intersecting_segmentIDs{},segment_id,
    LEAVE_ORIG = No
    LIST_NAME = Intersection_List{}.segment_id
    LIST_ACTION = Rename
    -> ListRenamer_2
ListRenamer_2
    LIST_COMPONENT_NAMES = intersecting_street_names{},gml_name{},gml_name,
    LEAVE_ORIG = No
    LIST_NAME = intersecting_street_names{}.gml_name
    LIST_ACTION = Rename
    -> UUIDGenerator_15
UUIDGenerator_15
    UUID_ATTR = _uuid
    -> StringConcatenator_15
StringConcatenator_15
    ACTION = Create New Attribute
    VAL_ATTR = gml_id
    PARM_LINE = @Value(id)@Value(_uuid)
    -> AreaCalculator_10
AreaCalculator_10
    AREA_ATTR = intersection_area_sqm
    AREA_TYPE = Plane Area
    MULT = 1
    -> AttributeRounder_10
AttributeRounder_10
    SRC_ATTRS = intersection_area_sqm
    ROUND_TYPE = Nearest
    PLACES = 3
    -> AttributeRemover_10
AttributeRemover_10
    REMOVE_ATTRS = id,source_id,sub_code,sanitation_district_boundary_indicator,_uuid
    -> Orientor_7
Orientor_7
    KIND = LEFT_HAND_RULE
    ORIENTED -> FaceReplacer_4
FaceReplacer_4
    THICKNESS_TOLERANCE_CHOICE = Automatic
    ANGULAR_TOLERANCE = 0.0
    THICKNESS_TOLERANCE = 0.0
    ANGULAR_TOLERANCE_CHOICE = Automatic
    -> GeometryColorSetter_8
GeometryColorSetter_8
    FILL_COLOR = 0.623529,0.623529,0.623529
    SIDE = Front
    MODE = Fixed
    ALPHA = 1
    COLORED -> Aggregator_12
Aggregator_12
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeRemover_21
AttributeRemover_21
    REMOVE_ATTRS = _part_number,_hierarchy_id,_hierarchy_child_id_list{0},_geometry_name,_hierarchy_parent_id
    -> AttributeCreator_35
AttributeCreator_35
    ATTR_TABLE:
      SET_TO road_id = road_@Value(gml_id)
      SET_TO gml_name = Intersection_@Value(intersecting_street_names_conc)
    -> AttributeCreator_36
    -> AttributeCreator_37
AttributeCreator_36
    ATTR_TABLE = SET_TO gml_parent_id = @Value(road_id)
    -> CityGMLGeometrySetter
CityGMLGeometrySetter
    ROLE = trafficArea
    GEOM = lod3MultiSurface
    -> GeometryPropertySetter_4
GeometryPropertySetter_4
    SRC_ATTRS = citygml_lod_name
    OVERWRITE_CHOICE = Yes
    SETTYPE_PARAM = Traits From Attributes
    REMOVE_ATTRIBUTE = No
    SET -> Road (writer CITYGML_3)
    SET -> Intersections
Intersections: Inspector
Road (writer CITYGML_3) [off]
    attributes: citygml_class xml_buffer, citygml_creationDate xml_date, citygml_feature_role xml_buffer, citygml_feature_role_attr_name xml_buffer, citygml_feature_role_attr_val xml_buffer, citygml_function{0} xml_char(200), citygml_level_of_detail{0} xml_char(200), citygml_surfaceMaterial xml_char(200), citygml_target_uri xml_buffer, citygml_terminationDate xml_date, citygml_usage{0} xml_char(200), construction_status xml_buffer, externalReference{0}.externalObject.name xml_xml, externalReference{0}.informationSystem xml_xml, gml_description xml_buffer, gml_name xml_buffer, gml_name{} xml_char(200), gml_name{0} xml_char(200), gml_name{1} xml_char(200), gml_name{2} xml_char(200), gml_name{3} xml_char(200), gml_name{4} xml_char(200), gml_name{5} xml_char(200), gml_name{6} xml_char(200), gml_name{7} xml_char(200), gml_name{8} xml_char(200), gml_name{9} xml_char(200), gml_name{10} xml_char(200), intersecting_segements_count xml_char(200), intersecting_segmentIDs_conc xml_char(200),
      intersecting_segmentIDs{} xml_char(200), intersecting_street_names_conc xml_char(200), intersection_area_sqm xml_char(200), road_id xml_char(200), snow_priority xml_buffer, special_address_place_name xml_buffer, special_address_place_name_2 xml_buffer, special_address_place_name_3 xml_buffer, special_address_place_name_4 xml_buffer, special_address_place_name_5 xml_buffer, special_address_type xml_buffer, special_address_type_2 xml_buffer, special_address_type_3 xml_buffer, special_address_type_4 xml_buffer, special_address_type_5 xml_buffer
AttributeCreator_37
    ATTR_TABLE:
      SET_TO gml_id = @Value(road_id)
      SET_TO gml_parent_id = NYC
      SET_TO href{0} = @Value(gml_id)
    -> GeometryRemover_5
GeometryRemover_5
    -> AttributeKeeper_19
AttributeKeeper_19
    KEEP_ATTRS = gml_parent_id,href{0},gml_id,gml_name

Bookmark: Plaza Manhattan Shape
Plazas_Extract (reader ESRISHAPE_6) [off]
    attributes: status char(254), feat_code number(33,31), shape_leng number(33,31), shape_area number(33,31), source_id number(33,31), sub_code number(33,31)
    -> CsmapReprojector_6

Bookmark: Edit Plaza
CsmapReprojector_6
    RASTER_CELL_SIZE = Preserve Cells
    VERTICAL_HANDLING = Ignore heights and leave them unchanged
    DEST = EPSG:32118
    INTERPOLATION_TYPE_NAME = Nearest Neighbor
    REPROJECTED -> AreaCalculator_9
AreaCalculator_9
    AREA_ATTR = plaza_area_sqm
    AREA_TYPE = Plane Area
    MULT = 1
    -> Extruder
Extruder
    DISTANCE = 0.1524
    DIRECTION = Auto
    -> VolumeCalculator_2
VolumeCalculator_2
    SET_TRAIT = No
    MULT = 1
    VOLUME_ATTR = plaza_volume_cubicmeter
    -> AttributeRounder_6
AttributeRounder_6
    SRC_ATTRS = plaza_volume_cubicmeter plaza_area_sqm
    ROUND_TYPE = Nearest
    PLACES = 3
    -> AttributeCreator_17
AttributeCreator_17
    ATTR_TABLE:
      SET_TO citygml_class = @Value(sub_code)
      SET_TO citygml_function{0} = 5
      SET_TO citygml_usage{0} = 1
      SET_TO citygml_target_uri = http://www.opengis.net/citygml/transportation/2.0
      SET_TO gml_name = Plaza
      SET_TO externalReference{0}.externalObject.name = @Value(source_id)
      SET_TO citygml_surfaceMaterial = 9999
      SET_TO citygml_creationDate = 2016-12-07
      SET_TO externalReference{0}.informationSystem = https://data.cityofnewyork.us/Transportation/Plazas/m4mp-ji5y/data
      SET_TO id = id_
      SET_TO gml_parent_id = NYC_Square
      SET_TO plaza_height_inch = 6
      SET_TO plaza_height_meter = 0.1524
    -> UUIDGenerator_9
UUIDGenerator_9
    UUID_ATTR = _uuid
    -> StringConcatenator_9
StringConcatenator_9
    ACTION = Create New Attribute
    VAL_ATTR = gml_id
    PARM_LINE = @Value(id)@Value(_uuid)
    -> Deaggregator_6
Deaggregator_6
    PART_NUMBER_FIELD = _part_number
    GEOM_NAME_FIELD = _geometry_name
    EXPLODE_INSTANCES = No
    LIST_ATTR_MODE_LOOKUP = LEAN
    MODE = Flatten One Level
    SPLIT_COMPOSITES = Yes
    DEAGGREGATED -> GeometryCoercer_4
GeometryCoercer_4
    GQUERY:
      for $geom in //geometry
      where $geom/count(parent::geometry) = 0
      return number($geom/@fme_id)
    KIND = fme_composite_surface
    COERCED -> Deaggregator_7
Deaggregator_7
    PART_NUMBER_FIELD = _part_number
    GEOM_NAME_FIELD = _geometry_name
    EXPLODE_INSTANCES = No
    LIST_ATTR_MODE_LOOKUP = LEAN
    MODE = Flatten One Level
    SPLIT_COMPOSITES = Yes
    DEAGGREGATED -> BoundsExtractor_3
BoundsExtractor_3
    XMAX = _xmax
    XMIN = _xmin
    ZMAX = _zmax
    ZMIN = _zmin
    YMIN = _ymin
    YMAX = _ymax
    -> Tester_24
Tester_24
    TEST_CLAUSE:
      TEST @Value(_zmin) = @Value(_zmax)
      TEST @Value(_zmin) != 0
    TEST_MODE = Automatic
    TEST_DESCRIPTION = ""
    BOOL_OP = AND
    PASSED -> Aggregator_4
    FAILED -> Tester_25
Aggregator_4
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeCreator_42
AttributeCreator_42
    ATTR_TABLE = SET_TO surfaceType = cover_surface
    -> AttributeCreator_13
Tester_25
    TEST_CLAUSE = TEST @Value(_zmax) != 0
    TEST_MODE = Automatic
    TEST_DESCRIPTION = ""
    BOOL_OP = OR
    PASSED -> Aggregator_5
Aggregator_5
    AGGREGATE_TYPE = Homogeneous Collection (If Possible)
    ORDERED = No
    SEP = ,
    GROUP_BY = gml_id
    MODE = Geometry - Assemble One Level
    ACCUM_ATTRS_NAME = Get Attributes From One Representative Feature
    AGGREGATE -> AttributeCreator_43
AttributeCreator_43
    ATTR_TABLE = SET_TO surfaceType = side_surface
    -> AttributeCreator_13
AttributeCreator_13
    ATTR_TABLE = SET_TO square_id = square_@Value(gml_id)
    -> UUIDGenerator_8
UUIDGenerator_8
    UUID_ATTR = _uuid
    -> StringConcatenator_8
StringConcatenator_8
    ACTION = Create New Attribute
    VAL_ATTR = gml_id
    PARM_LINE = @Value(id)@Value(_uuid)
    -> AttributeCreator_31
AttributeCreator_31
    ATTR_TABLE = SET_TO gml_parent_id = @Value(square_id)
    -> CityGMLGeometrySetter_11
CityGMLGeometrySetter_11
    ROLE = trafficArea
    GEOM = lod3MultiSurface
    -> GeometryPropertySetter_12
GeometryPropertySetter_12
    SRC_ATTRS = citygml_lod_name
    OVERWRITE_CHOICE = Yes
    SETTYPE_PARAM = Traits From Attributes
    REMOVE_ATTRIBUTE = No
    SET -> GeometryColorSetter_2
GeometryColorSetter_2
    FILL_COLOR = 0.529412,0.34902,0.34902
    SIDE = Both
    MODE = Fixed
    ALPHA = 1
    COLORED -> Square (writer CITYGML_7)
    COLORED -> Plaza

Bookmark: Input Data Manhattan
Note: Coodrinate transformation to EPSG:32118

FME custom transformer CityGMLGeometrySetter
This transformer provides a convenient way to set both the CityGML LOD Name and role from a preset list of options.
Input Ports
    Input
    Features to tag with City LOD name and feature role 
    Output Ports
    Output
    Features tagged with City LOD name and feature role 
    Parameters
    CityGML Lod Name
    Select the desired CityGML Lod name
    Feature Role
    Select the desired feature role

Parameters:
- GEOM =   # CityGML Lod Name
- ROLE =   # Feature Role

INPUT (input)
    -> AttributeCreator
Note: Set LOD name / and citygml role
AttributeCreator
    ATTR_TABLE:
      SET_TO citygml_lod_name = $(GEOM)
      SET_TO citygml_feature_role = $(ROLE)
    -> GeometryPropertySetter
Note: Convert LOD to geometry trait
GeometryPropertySetter
    SRC_ATTRS = citygml_lod_name
    OVERWRITE_CHOICE = Yes
    SETTYPE_PARAM = Traits From Attributes
    REMOVE_ATTRIBUTE = No
    SET -> OUTPUT (output)
OUTPUT (output)
