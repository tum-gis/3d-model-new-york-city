FME workspace 3_NYC_add_Track_Centerline_to_lod0Network.fmw

Parameters:
- SourceDataset_CITYGML = Y:\TUM Geoinformatik\City Model NYC\Datengrundlage\Mittelachsen CityGML\Streetspace_LoD0.gml   # Source CityGML File(s)
- SourceDataset_ESRISHAPE_3 = C:\Users\cbeil\Downloads\Bike Routes\geo_export_42d3005a-506a-4ab1-8aa6-8e3ba879dbaa.shp   # Source Esri Shapefile(s)
- DestDataset_CITYGML = E:\New York City\Output\lod0Network_Road&Track_NYC.gml   # Destination CityGML Document
- SourceDataset_ESRISHAPE = C:\Users\cbeil\Downloads\Sidewalk Centerline\geo_export_a137ae28-0719-40b0-8bd7-bf524c3538f9.shp   # Source Esri Shapefile(s)
- SourceDataset_CITYGML_3 = E:\TUM Geoinformatik\City Model NYC\Datengrundlage\Planimetrics\Sidewalk Centerline\geo_export_02d686d9-8957-4f97-864a-f01b1aa3778d.shp   # Source CityGML File(s)

Readers:
- CITYGML_1: CITYGML from $(SourceDataset_CITYGML)
- ESRISHAPE_1: ESRISHAPE from $(SourceDataset_ESRISHAPE_3)
- CITYGML_2: CITYGML from $(SourceDataset_CITYGML_3)
- ESRISHAPE_2: ESRISHAPE from $(SourceDataset_ESRISHAPE)

Writers:
- CITYGML_3: CITYGML to $(DestDataset_CITYGML)

Track: Inspector [off]
Track (writer CITYGML_3) [off]
    attributes: citygml_class xml_buffer, citygml_function{} xml_char(200), citygml_level_of_detail{0} xml_char(200), citygml_target_uri  xml_char(200), track_length_2D_meter xml_char(200)
Road (writer CITYGML_3) [off]
    attributes: bike_lane xml_buffer, bike_lane_dir xml_char(200), bike_lane_from xml_char(200), bike_lane_onoff xml_char(200), bike_lane_to xml_char(200), citygml_appearance{}.xlink_href xml_buffer, citygml_auxiliary_traffic_area{}.xlink_href xml_buffer, citygml_class xml_buffer, citygml_creationDate xml_date, citygml_feature_role xml_buffer, citygml_feature_role_attr_name xml_buffer, citygml_feature_role_attr_val xml_buffer, citygml_function{} xml_buffer, citygml_generalizes_to{}.xlink_href xml_buffer, citygml_level_of_detail{} xml_buffer, citygml_target_uri xml_buffer, citygml_terminationDate xml_date, citygml_traffic_area{}.xlink_href xml_buffer, citygml_usage{} xml_buffer, construction_status xml_buffer, curve_flag xml_buffer, externalReference{}.externalObject.name xml_xml, externalReference{}.externalObject.uri xml_xml, externalReference{}.informationSystem xml_xml, externalReference{}.informationSystem  xml_buffer, face_code xml_buffer, gml_description xml_buffer, gml_name xml_buffer, level_end_segment xml_buffer, level_start_segment xml_buffer,
      merge_bike_lane xml_buffer, merge_citygml_class xml_buffer, merge_citygml_function xml_buffer, merge_construction_status xml_buffer, merge_curve_flag xml_buffer, merge_face_code xml_buffer, merge_gml_name xml_buffer, merge_level_end_segment xml_buffer, merge_level_start_segment xml_buffer, merge_non_pedestrian xml_buffer, merge_physical_id xml_buffer, merge_radius_arc xml_buffer, merge_sanitation_district_boundary_indicator xml_buffer, merge_segment_count xml_buffer, merge_segment_id xml_buffer, merge_segment_type xml_buffer, merge_sequence_number xml_buffer, merge_snow_priority xml_buffer, merge_street_code xml_buffer, merge_traffic_direction xml_buffer, merge_traffic_direction_source xml_buffer, merge2_citygml_class xml_buffer, merge2_citygml_function xml_buffer, merge2_construction_status xml_buffer, merge2_curve_flag xml_buffer, merge2_face_code xml_buffer, merge2_gml_name xml_buffer, merge2_level_end_segment xml_buffer, merge2_level_start_segment xml_buffer, merge2_non_pedestrian xml_buffer,
      merge2_physical_id xml_buffer, merge2_radius_arc xml_buffer, merge2_segment_count xml_buffer, merge2_segment_id xml_buffer, merge2_segment_type xml_buffer, merge2_sequence_number xml_buffer, merge2_snow_priority xml_buffer, merge2_street_code xml_buffer, merge2_traffic_direction xml_buffer, merge2_traffic_direction_source xml_buffer, merge3_citygml_class xml_buffer, merge3_citygml_function xml_buffer, merge3_construction_status xml_buffer, merge3_curve_flag xml_buffer, merge3_face_code xml_buffer, merge3_gml_name xml_buffer, merge3_level_end_segment xml_buffer, merge3_level_start_segment xml_buffer, merge3_non_pedestrian xml_buffer, merge3_physical_id xml_buffer, merge3_radius_arc xml_buffer, merge3_segment_count xml_buffer, merge3_segment_id xml_buffer, merge3_segment_type xml_buffer, merge3_sequence_number xml_buffer, merge3_snow_priority xml_buffer, merge3_street_code xml_buffer, merge3_traffic_direction xml_buffer, merge3_traffic_direction_source xml_buffer, merge4_citygml_class xml_buffer,
      merge4_citygml_function xml_buffer, merge4_construction_status xml_buffer, merge4_face_code xml_buffer, merge4_gml_name xml_buffer, merge4_level_end_segment xml_buffer, merge4_level_start_segment xml_buffer, merge4_non_pedestrian xml_buffer, merge4_physical_id xml_buffer, merge4_radius_arc xml_buffer, merge4_segment_count xml_buffer, merge4_segment_id xml_buffer, merge4_segment_type xml_buffer, merge4_sequence_number xml_buffer, merge4_snow_priority xml_buffer, merge4_street_code xml_buffer, merge4_traffic_direction xml_buffer, merge4_traffic_direction_source xml_buffer, node_id_from xml_buffer, node_id_to xml_buffer, non_pedestrian xml_buffer, number_parking_lanes xml_buffer, number_total_lanes xml_buffer, number_travel_lanes xml_buffer, physical_id xml_buffer, radius_arc xml_buffer, sanitation_district_boundary_indicator xml_buffer, segment_count xml_buffer, segment_id xml_buffer, segment_type xml_buffer, sequence_number xml_buffer,
      slope_percent xml_buffer, snow_priority xml_buffer, special_address_place_name xml_buffer, special_address_place_name_2 xml_buffer, special_address_place_name_3 xml_buffer, special_address_place_name_4 xml_buffer, special_address_place_name_5 xml_buffer, special_address_place_name_6 xml_buffer, special_address_place_name_7 xml_buffer, special_address_place_name_8 xml_buffer, special_address_place_name_9 xml_buffer, special_address_type xml_buffer, special_address_type_2 xml_buffer, special_address_type_3 xml_buffer, special_address_type_4 xml_buffer, special_address_type_5 xml_buffer, special_address_type_6 xml_buffer, special_address_type_7 xml_buffer, special_address_type_8 xml_buffer, special_address_type_9 xml_buffer, street_code xml_buffer, street_length_2D_meter xml_buffer, street_length_3D_meter xml_buffer, street_pavement_rating_date xml_buffer, street_pavement_rating_num xml_buffer, street_pavement_rating_text xml_buffer, street_segment_width_meter xml_buffer, street_speed_limit_km_h xml_buffer, street_speed_limit_mph xml_buffer, street_width_meter xml_buffer,
      traffic_direction xml_buffer, traffic_direction_source xml_buffer

Bookmark: Interior Sidewalk Centerlines
geo_export_a137ae28-0719-40b0-8bd7-bf524c3538f9 (reader ESRISHAPE_2) [off]
    attributes: feat_code number(33,31), source_id number(33,31), shape_leng number(33,31), status char(254), sub_code number(33,31)
    -> CsmapReprojector

Bookmark: Coordinate Transformation to EPSG:32118
Note: Transform Input data to EPSG:32118
CsmapReprojector
    RASTER_CELL_SIZE = Preserve Cells
    DEST = EPSG:32118
    INTERPOLATION_TYPE_NAME = Nearest Neighbor
    VERTICAL_HANDLING = Ignore heights and leave them unchanged
    REPROJECTED -> AttributeCreator
CsmapReprojector_2
    RASTER_CELL_SIZE = Preserve Cells
    DEST = EPSG:32118
    INTERPOLATION_TYPE_NAME = Nearest Neighbor
    VERTICAL_HANDLING = Ignore heights and leave them unchanged
    REPROJECTED -> AttributeRemover_2

Bookmark: Semantic manipulation
AttributeCreator
    ATTR_TABLE:
      SET_TO citygml_function{0} = 2
      SET_TO citygml_class = @Value(sub_code)
      SET_TO citygml_level_of_detail{0} = 0
      SET_TO citygml_target_uri  = http://www.opengis.net/citygml/transportation/1.0
      SET_TO externalReference{0}.externalObject.name = @Value(source_id)
      SET_TO externalReference{0}.informationSystem = https://data.cityofnewyork.us/dataset/Sidewalk-Centerline/a9xv-vek9/data
      SET_TO id = id_
    -> LengthCalculator
LengthCalculator
    LEN_ATTR = track_length_2D_meter
    MULT = 1
    DIM = 2
    -> AttributeRounder
AttributeRounder
    PLACES = 3
    ROUND_TYPE = Nearest
    SRC_ATTRS = track_length_2D_meter
    -> UUIDGenerator
UUIDGenerator
    UUID_ATTR = _uuid
    -> StringConcatenator
StringConcatenator
    ACTION = Create New Attribute
    VAL_ATTR = gml_id
    PARM_LINE = @Value(id)@Value(_uuid)
    -> AttributeRemover
AttributeRemover
    REMOVE_ATTRS = _uuid,id,status,shape_leng,sub_code,feat_code,source_id
    -> AttributeEncoder
AttributeEncoder
    DEST_ENCODING = utf-16
    TREAT_AS_BYTES = Honor Encoding
    ATTRCHOICE = All Attributes
    -> ListPopulator
ListPopulator
    PREFIX = citygml_function
    LIST_NAME = citygml_function
    -> CityGMLGeometrySetter
CityGMLGeometrySetter
    ROLE = cityObjectMember
    GEOM = lod0Network
    -> GeometryPropertySetter
GeometryPropertySetter
    SETTYPE_PARAM = Traits From Attributes
    OVERWRITE_CHOICE = Yes
    REMOVE_ATTRIBUTE = No
    SRC_ATTRS = citygml_lod_name
    SET -> Track (writer CITYGML_3)
    SET -> Track
AttributeRemover_2
    REMOVE_ATTRS = _overlaps
    -> FeatureMerger [REQUESTOR]
GeometryRemover
    -> AttributeKeeper
AttributeKeeper
    KEEP_ATTRS = fromstreet,tostreet,lanecount,segment_id,onoffst,bikedir
    -> AttributeRenamer
AttributeRenamer
    ATTR_TABLE:
      RENAME_SET_DEFAULT lanecount > bike_lane
      RENAME_SET_DEFAULT fromstreet > bike_lane_from
      RENAME_SET_DEFAULT tostreet > bike_lane_to
      RENAME_SET_DEFAULT onoffst > bike_lane_onoff
      RENAME_SET_DEFAULT bikedir > bike_lane_dir
    -> FeatureMerger [SUPPLIER]
Note: Add additional information on bike routes via corresponding attribute 'segment_id'
FeatureMerger
    ATTR_ACCUM_MODE = Merge Supplier
    REJECT_NULL_MISSING_KEYS = No
    PROCESS_DUPS = No
    JOIN_KEYS = @Value(segment_id) @Value(segment_id) AUTO
    IGNORE_NULLS = No
    MERGE_TYPE = Attributes Only
    ATTR_CONFLICT_RES = Use Requestor
    SUPPLIERS_FIRST = No
    MERGED -> CityGMLGeometrySetter_2
    NOT_MERGED -> CityGMLGeometrySetter_2
CityGMLGeometrySetter_2
    ROLE = cityObjectMember
    GEOM = lod0Network
    -> GeometryPropertySetter_2
GeometryPropertySetter_2
    SETTYPE_PARAM = Traits From Attributes
    OVERWRITE_CHOICE = Yes
    REMOVE_ATTRIBUTE = No
    SRC_ATTRS = citygml_lod_name
    SET -> Road (writer CITYGML_3)

Bookmark: Street Centerlines
Road (reader CITYGML_1) [off]
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_function{} xml_buffer, citygml_usage{} xml_buffer, citygml_traffic_area{}.xlink_href xml_buffer, citygml_auxiliary_traffic_area{}.xlink_href xml_buffer, citygml_level_of_detail{} xml_buffer, _overlaps xml_buffer, bike_lane xml_buffer, citygml_class xml_buffer, construction_status xml_buffer, curve_flag xml_buffer, externalReference{}.informationSystem  xml_buffer, face_code xml_buffer, level_end_segment xml_buffer, level_start_segment xml_buffer, merge2_citygml_class xml_buffer, merge2_citygml_function xml_buffer, merge2_construction_status xml_buffer,
      merge2_curve_flag xml_buffer, merge2_face_code xml_buffer, merge2_gml_name xml_buffer, merge2_level_end_segment xml_buffer, merge2_level_start_segment xml_buffer, merge2_non_pedestrian xml_buffer, merge2_physical_id xml_buffer, merge2_radius_arc xml_buffer, merge2_segment_count xml_buffer, merge2_segment_id xml_buffer, merge2_segment_type xml_buffer, merge2_sequence_number xml_buffer, merge2_snow_priority xml_buffer, merge2_street_code xml_buffer, merge2_traffic_direction xml_buffer, merge2_traffic_direction_source xml_buffer, merge3_citygml_class xml_buffer, merge3_citygml_function xml_buffer, merge3_construction_status xml_buffer, merge3_curve_flag xml_buffer, merge3_face_code xml_buffer, merge3_gml_name xml_buffer, merge3_level_end_segment xml_buffer, merge3_level_start_segment xml_buffer, merge3_non_pedestrian xml_buffer, merge3_physical_id xml_buffer, merge3_radius_arc xml_buffer, merge3_segment_count xml_buffer, merge3_segment_id xml_buffer, merge3_segment_type xml_buffer,
      merge3_sequence_number xml_buffer, merge3_snow_priority xml_buffer, merge3_street_code xml_buffer, merge3_traffic_direction xml_buffer, merge3_traffic_direction_source xml_buffer, merge4_citygml_class xml_buffer, merge4_citygml_function xml_buffer, merge4_construction_status xml_buffer, merge4_face_code xml_buffer, merge4_gml_name xml_buffer, merge4_level_end_segment xml_buffer, merge4_level_start_segment xml_buffer, merge4_non_pedestrian xml_buffer, merge4_physical_id xml_buffer, merge4_radius_arc xml_buffer, merge4_segment_count xml_buffer, merge4_segment_id xml_buffer, merge4_segment_type xml_buffer, merge4_sequence_number xml_buffer, merge4_snow_priority xml_buffer, merge4_street_code xml_buffer, merge4_traffic_direction xml_buffer, merge4_traffic_direction_source xml_buffer, merge_bike_lane xml_buffer, merge_citygml_class xml_buffer, merge_citygml_function xml_buffer, merge_construction_status xml_buffer, merge_curve_flag xml_buffer, merge_face_code xml_buffer, merge_gml_name xml_buffer,
      merge_level_end_segment xml_buffer, merge_level_start_segment xml_buffer, merge_non_pedestrian xml_buffer, merge_physical_id xml_buffer, merge_radius_arc xml_buffer, merge_sanitation_district_boundary_indicator xml_buffer, merge_segment_count xml_buffer, merge_segment_id xml_buffer, merge_segment_type xml_buffer, merge_sequence_number xml_buffer, merge_snow_priority xml_buffer, merge_street_code xml_buffer, merge_traffic_direction xml_buffer, merge_traffic_direction_source xml_buffer, node_id_from xml_buffer, node_id_to xml_buffer, non_pedestrian xml_buffer, number_parking_lanes xml_buffer, number_total_lanes xml_buffer, number_travel_lanes xml_buffer, physical_id xml_buffer, radius_arc xml_buffer, sanitation_district_boundary_indicator xml_buffer, segment_count xml_buffer, segment_id xml_buffer, segment_type xml_buffer, sequence_number xml_buffer, slope_percent xml_buffer, snow_priority xml_buffer, special_address_place_name xml_buffer,
      special_address_place_name_2 xml_buffer, special_address_place_name_3 xml_buffer, special_address_place_name_4 xml_buffer, special_address_place_name_5 xml_buffer, special_address_place_name_6 xml_buffer, special_address_place_name_7 xml_buffer, special_address_place_name_8 xml_buffer, special_address_place_name_9 xml_buffer, special_address_type xml_buffer, special_address_type_2 xml_buffer, special_address_type_3 xml_buffer, special_address_type_4 xml_buffer, special_address_type_5 xml_buffer, special_address_type_6 xml_buffer, special_address_type_7 xml_buffer, special_address_type_8 xml_buffer, special_address_type_9 xml_buffer, street_area_2D_sq_m xml_buffer, street_code xml_buffer, street_length_2D_meter xml_buffer, street_length_3D_meter xml_buffer, street_pavement_rating_date xml_buffer, street_pavement_rating_num xml_buffer, street_pavement_rating_text xml_buffer, street_segment_width_meter xml_buffer, street_speed_limit_km_h xml_buffer, street_speed_limit_mph xml_buffer, street_width_meter xml_buffer, traffic_direction xml_buffer, traffic_direction_source xml_buffer
    -> CsmapReprojector_2

Bookmark: Bike Routes
geo_export_42d3005a-506a-4ab1-8aa6-8e3ba879dbaa (reader ESRISHAPE_1) [off]
    attributes: tf_facilit char(254), comments char(254), bikedir char(254), ft_facilit char(254), objectid_1 number(33,31), allclasses char(254), date_instd date, time_instd char(254), lanecount number(33,31), segment_id char(254), boro number(33,31), street char(254), date_modda date, time_modda char(254), tostreet char(254), fromstreet char(254), onoffst char(254)
    -> GeometryRemover

FME custom transformer CityGMLGeometrySetter
This transformer provides a convenient way to set both the CityGML LOD Name and role from a preset list of options.
Input Ports
    Input
    Features to tag with City LOD name and feature role 
    Output Ports
    Output
    Features tagged with City LOD name and feature role 
    Parameters
    CityGML Lod Name
    Select the desired CityGML Lod name
    Feature Role
    Select the desired feature role

Parameters:
- GEOM =   # CityGML Lod Name
- ROLE =   # Feature Role

Input (input)
    -> AttributeCreator
Note: Set LOD name / and citygml role
AttributeCreator
    ATTR_TABLE:
      SET_TO citygml_lod_name = $(GEOM)
      SET_TO citygml_feature_role = $(ROLE)
    -> GeometryPropertySetter
Note: Convert LOD to geometry trait
GeometryPropertySetter
    SETTYPE_PARAM = Traits From Attributes
    OVERWRITE_CHOICE = Yes
    REMOVE_ATTRIBUTE = No
    GQUERY:
      for $geom in //geometry
      where $geom/count(parent::geometry) = 0
      return number($geom/@fme_id)
    SRC_ATTRS = citygml_lod_name
    SET -> Output (output)
Output (output)
