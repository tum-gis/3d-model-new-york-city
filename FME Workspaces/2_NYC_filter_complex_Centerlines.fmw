FME workspace 2_NYC_filter_complex_Centerlines.fmw

Parameters:
- DestDataset_CITYGML = H:\Masterarbeit\Umsetzung\Output\LoD0\Centerlines_unfiltered   # Destination CityGML Document
- SourceDataset_CITYGML_3 = H:\Masterarbeit\Umsetzung\Output\LoD0\Streetspace_LoD0.gml   # Source CityGML File(s)
- DestDataset_CITYGML_4 = H:\Masterarbeit\Umsetzung\Output\LoD0\Centerlines_filtered.gml   # Destination CityGML Document

Readers:
- CITYGML_1: CITYGML from $(SourceDataset_CITYGML_3)

Writers:
- CITYGML_2: CITYGML to $(DestDataset_CITYGML)
- CITYGML_3: CITYGML to $(DestDataset_CITYGML_4)

Note: This Workspace filters complex centerlines. These centerlines a re identified using different attributes and characteristics such as inforomation on 'ramps', 'motorways' or hight-level.
Road (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_function{} xml_buffer, citygml_usage{} xml_buffer, citygml_traffic_area{}.xlink_href xml_buffer, citygml_auxiliary_traffic_area{}.xlink_href xml_buffer, citygml_level_of_detail{} xml_buffer, _overlaps xml_buffer, bike_lane xml_buffer, citygml_class xml_buffer, construction_status xml_buffer, curve_flag xml_buffer, externalReference{}.informationSystem  xml_buffer, face_code xml_buffer, level_end_segment xml_buffer, level_start_segment xml_buffer, merge2_citygml_class xml_buffer, merge2_citygml_function xml_buffer, merge2_construction_status xml_buffer,
      merge2_curve_flag xml_buffer, merge2_face_code xml_buffer, merge2_gml_name xml_buffer, merge2_level_end_segment xml_buffer, merge2_level_start_segment xml_buffer, merge2_non_pedestrian xml_buffer, merge2_physical_id xml_buffer, merge2_radius_arc xml_buffer, merge2_segment_count xml_buffer, merge2_segment_id xml_buffer, merge2_segment_type xml_buffer, merge2_sequence_number xml_buffer, merge2_snow_priority xml_buffer, merge2_street_code xml_buffer, merge2_traffic_direction xml_buffer, merge2_traffic_direction_source xml_buffer, merge3_citygml_class xml_buffer, merge3_citygml_function xml_buffer, merge3_construction_status xml_buffer, merge3_curve_flag xml_buffer, merge3_face_code xml_buffer, merge3_gml_name xml_buffer, merge3_level_end_segment xml_buffer, merge3_level_start_segment xml_buffer, merge3_non_pedestrian xml_buffer, merge3_physical_id xml_buffer, merge3_radius_arc xml_buffer, merge3_segment_count xml_buffer, merge3_segment_id xml_buffer, merge3_segment_type xml_buffer,
      merge3_sequence_number xml_buffer, merge3_snow_priority xml_buffer, merge3_street_code xml_buffer, merge3_traffic_direction xml_buffer, merge3_traffic_direction_source xml_buffer, merge4_citygml_class xml_buffer, merge4_citygml_function xml_buffer, merge4_construction_status xml_buffer, merge4_face_code xml_buffer, merge4_gml_name xml_buffer, merge4_level_end_segment xml_buffer, merge4_level_start_segment xml_buffer, merge4_non_pedestrian xml_buffer, merge4_physical_id xml_buffer, merge4_radius_arc xml_buffer, merge4_segment_count xml_buffer, merge4_segment_id xml_buffer, merge4_segment_type xml_buffer, merge4_sequence_number xml_buffer, merge4_snow_priority xml_buffer, merge4_street_code xml_buffer, merge4_traffic_direction xml_buffer, merge4_traffic_direction_source xml_buffer, merge_bike_lane xml_buffer, merge_citygml_class xml_buffer, merge_citygml_function xml_buffer, merge_construction_status xml_buffer, merge_curve_flag xml_buffer, merge_face_code xml_buffer, merge_gml_name xml_buffer,
      merge_level_end_segment xml_buffer, merge_level_start_segment xml_buffer, merge_non_pedestrian xml_buffer, merge_physical_id xml_buffer, merge_radius_arc xml_buffer, merge_sanitation_district_boundary_indicator xml_buffer, merge_segment_count xml_buffer, merge_segment_id xml_buffer, merge_segment_type xml_buffer, merge_sequence_number xml_buffer, merge_snow_priority xml_buffer, merge_street_code xml_buffer, merge_traffic_direction xml_buffer, merge_traffic_direction_source xml_buffer, node_id_from xml_buffer, node_id_to xml_buffer, non_pedestrian xml_buffer, number_parking_lanes xml_buffer, number_total_lanes xml_buffer, number_travel_lanes xml_buffer, physical_id xml_buffer, radius_arc xml_buffer, sanitation_district_boundary_indicator xml_buffer, segment_count xml_buffer, segment_id xml_buffer, segment_type xml_buffer, sequence_number xml_buffer, slope_percent xml_buffer, snow_priority xml_buffer, special_address_place_name xml_buffer,
      special_address_place_name_2 xml_buffer, special_address_place_name_3 xml_buffer, special_address_place_name_4 xml_buffer, special_address_place_name_5 xml_buffer, special_address_place_name_6 xml_buffer, special_address_place_name_7 xml_buffer, special_address_place_name_8 xml_buffer, special_address_place_name_9 xml_buffer, special_address_type xml_buffer, special_address_type_2 xml_buffer, special_address_type_3 xml_buffer, special_address_type_4 xml_buffer, special_address_type_5 xml_buffer, special_address_type_6 xml_buffer, special_address_type_7 xml_buffer, special_address_type_8 xml_buffer, special_address_type_9 xml_buffer, street_area_2D_sq_m xml_buffer, street_code xml_buffer, street_length_2D_meter xml_buffer, street_length_3D_meter xml_buffer, street_pavement_rating_date xml_buffer, street_pavement_rating_num xml_buffer, street_pavement_rating_text xml_buffer, street_segment_width_meter xml_buffer, street_speed_limit_km_h xml_buffer, street_speed_limit_mph xml_buffer, street_width_meter xml_buffer, traffic_direction xml_buffer, traffic_direction_source xml_buffer,
      externalReference{0}.externalObject.name xml_xml, externalReference{1}.externalObject.name xml_xml, externalReference{2}.externalObject.name xml_xml, externalReference{0}.externalObject.uri xml_xml, externalReference{1}.externalObject.uri xml_xml, externalReference{2}.externalObject.uri xml_xml, externalReference{0}.informationSystem xml_xml, externalReference{1}.informationSystem xml_xml, externalReference{2}.informationSystem xml_xml
    -> Inspector
    -> Tester_2
Road (writer CITYGML_3)
    attributes: _overlaps xml_buffer, bike_lane xml_buffer, citygml_appearance{}.xlink_href xml_buffer, citygml_auxiliary_traffic_area{}.xlink_href xml_buffer, citygml_class xml_buffer, citygml_creationDate xml_date, citygml_feature_role xml_buffer, citygml_feature_role_attr_name xml_buffer, citygml_feature_role_attr_val xml_buffer, citygml_function{} xml_buffer, citygml_generalizes_to{}.xlink_href xml_buffer, citygml_level_of_detail{} xml_buffer, citygml_target_uri xml_buffer, citygml_terminationDate xml_date, citygml_traffic_area{}.xlink_href xml_buffer, citygml_usage{} xml_buffer, construction_status xml_buffer, curve_flag xml_buffer, externalReference{}.externalObject.name xml_xml, externalReference{}.externalObject.uri xml_xml, externalReference{}.informationSystem xml_xml, externalReference{}.informationSystem  xml_buffer, externalReference{0}.externalObject.name xml_xml, externalReference{0}.externalObject.uri xml_xml, externalReference{0}.informationSystem xml_xml, externalReference{1}.externalObject.name xml_xml, externalReference{1}.externalObject.uri xml_xml, externalReference{1}.informationSystem xml_xml, externalReference{2}.externalObject.name xml_xml, externalReference{2}.externalObject.uri xml_xml,
      externalReference{2}.informationSystem xml_xml, face_code xml_buffer, gml_description xml_buffer, gml_name xml_buffer, level_end_segment xml_buffer, level_start_segment xml_buffer, merge_bike_lane xml_buffer, merge_citygml_class xml_buffer, merge_citygml_function xml_buffer, merge_construction_status xml_buffer, merge_curve_flag xml_buffer, merge_face_code xml_buffer, merge_gml_name xml_buffer, merge_level_end_segment xml_buffer, merge_level_start_segment xml_buffer, merge_non_pedestrian xml_buffer, merge_physical_id xml_buffer, merge_radius_arc xml_buffer, merge_sanitation_district_boundary_indicator xml_buffer, merge_segment_count xml_buffer, merge_segment_id xml_buffer, merge_segment_type xml_buffer, merge_sequence_number xml_buffer, merge_snow_priority xml_buffer, merge_street_code xml_buffer, merge_traffic_direction xml_buffer, merge_traffic_direction_source xml_buffer, merge2_citygml_class xml_buffer, merge2_citygml_function xml_buffer, merge2_construction_status xml_buffer,
      merge2_curve_flag xml_buffer, merge2_face_code xml_buffer, merge2_gml_name xml_buffer, merge2_level_end_segment xml_buffer, merge2_level_start_segment xml_buffer, merge2_non_pedestrian xml_buffer, merge2_physical_id xml_buffer, merge2_radius_arc xml_buffer, merge2_segment_count xml_buffer, merge2_segment_id xml_buffer, merge2_segment_type xml_buffer, merge2_sequence_number xml_buffer, merge2_snow_priority xml_buffer, merge2_street_code xml_buffer, merge2_traffic_direction xml_buffer, merge2_traffic_direction_source xml_buffer, merge3_citygml_class xml_buffer, merge3_citygml_function xml_buffer, merge3_construction_status xml_buffer, merge3_curve_flag xml_buffer, merge3_face_code xml_buffer, merge3_gml_name xml_buffer, merge3_level_end_segment xml_buffer, merge3_level_start_segment xml_buffer, merge3_non_pedestrian xml_buffer, merge3_physical_id xml_buffer, merge3_radius_arc xml_buffer, merge3_segment_count xml_buffer, merge3_segment_id xml_buffer, merge3_segment_type xml_buffer,
      merge3_sequence_number xml_buffer, merge3_snow_priority xml_buffer, merge3_street_code xml_buffer, merge3_traffic_direction xml_buffer, merge3_traffic_direction_source xml_buffer, merge4_citygml_class xml_buffer, merge4_citygml_function xml_buffer, merge4_construction_status xml_buffer, merge4_face_code xml_buffer, merge4_gml_name xml_buffer, merge4_level_end_segment xml_buffer, merge4_level_start_segment xml_buffer, merge4_non_pedestrian xml_buffer, merge4_physical_id xml_buffer, merge4_radius_arc xml_buffer, merge4_segment_count xml_buffer, merge4_segment_id xml_buffer, merge4_segment_type xml_buffer, merge4_sequence_number xml_buffer, merge4_snow_priority xml_buffer, merge4_street_code xml_buffer, merge4_traffic_direction xml_buffer, merge4_traffic_direction_source xml_buffer, node_id_from xml_buffer, node_id_to xml_buffer, non_pedestrian xml_buffer, number_parking_lanes xml_buffer, number_total_lanes xml_buffer, number_travel_lanes xml_buffer, physical_id xml_buffer,
      radius_arc xml_buffer, sanitation_district_boundary_indicator xml_buffer, segment_count xml_buffer, segment_id xml_buffer, segment_type xml_buffer, sequence_number xml_buffer, slope_percent xml_buffer, snow_priority xml_buffer, special_address_place_name xml_buffer, special_address_place_name_2 xml_buffer, special_address_place_name_3 xml_buffer, special_address_place_name_4 xml_buffer, special_address_place_name_5 xml_buffer, special_address_place_name_6 xml_buffer, special_address_place_name_7 xml_buffer, special_address_place_name_8 xml_buffer, special_address_place_name_9 xml_buffer, special_address_type xml_buffer, special_address_type_2 xml_buffer, special_address_type_3 xml_buffer, special_address_type_4 xml_buffer, special_address_type_5 xml_buffer, special_address_type_6 xml_buffer, special_address_type_7 xml_buffer, special_address_type_8 xml_buffer, special_address_type_9 xml_buffer, street_area_2D_sq_m xml_buffer, street_code xml_buffer, street_length_2D_meter xml_buffer, street_length_3D_meter xml_buffer,
      street_pavement_rating_date xml_buffer, street_pavement_rating_num xml_buffer, street_pavement_rating_text xml_buffer, street_segment_width_meter xml_buffer, street_speed_limit_km_h xml_buffer, street_speed_limit_mph xml_buffer, street_width_meter xml_buffer, traffic_direction xml_buffer, traffic_direction_source xml_buffer
Road (writer CITYGML_2)
    attributes: _overlaps xml_buffer, bike_lane xml_buffer, citygml_appearance{}.xlink_href xml_buffer, citygml_auxiliary_traffic_area{}.xlink_href xml_buffer, citygml_class xml_buffer, citygml_creationDate xml_date, citygml_feature_role xml_buffer, citygml_feature_role_attr_name xml_buffer, citygml_feature_role_attr_val xml_buffer, citygml_function{} xml_buffer, citygml_generalizes_to{}.xlink_href xml_buffer, citygml_level_of_detail{} xml_buffer, citygml_target_uri xml_buffer, citygml_terminationDate xml_date, citygml_traffic_area{}.xlink_href xml_buffer, citygml_usage{} xml_buffer, construction_status xml_buffer, curve_flag xml_buffer, externalReference{}.externalObject.name xml_xml, externalReference{}.externalObject.uri xml_xml, externalReference{}.informationSystem xml_xml, externalReference{}.informationSystem  xml_buffer, externalReference{0}.externalObject.name xml_xml, externalReference{0}.externalObject.uri xml_xml, externalReference{0}.informationSystem xml_xml, externalReference{1}.externalObject.name xml_xml, externalReference{1}.externalObject.uri xml_xml, externalReference{1}.informationSystem xml_xml, externalReference{2}.externalObject.name xml_xml, externalReference{2}.externalObject.uri xml_xml,
      externalReference{2}.informationSystem xml_xml, face_code xml_buffer, gml_description xml_buffer, gml_name xml_buffer, level_end_segment xml_buffer, level_start_segment xml_buffer, merge_bike_lane xml_buffer, merge_citygml_class xml_buffer, merge_citygml_function xml_buffer, merge_construction_status xml_buffer, merge_curve_flag xml_buffer, merge_face_code xml_buffer, merge_gml_name xml_buffer, merge_level_end_segment xml_buffer, merge_level_start_segment xml_buffer, merge_non_pedestrian xml_buffer, merge_physical_id xml_buffer, merge_radius_arc xml_buffer, merge_sanitation_district_boundary_indicator xml_buffer, merge_segment_count xml_buffer, merge_segment_id xml_buffer, merge_segment_type xml_buffer, merge_sequence_number xml_buffer, merge_snow_priority xml_buffer, merge_street_code xml_buffer, merge_traffic_direction xml_buffer, merge_traffic_direction_source xml_buffer, merge2_citygml_class xml_buffer, merge2_citygml_function xml_buffer, merge2_construction_status xml_buffer,
      merge2_curve_flag xml_buffer, merge2_face_code xml_buffer, merge2_gml_name xml_buffer, merge2_level_end_segment xml_buffer, merge2_level_start_segment xml_buffer, merge2_non_pedestrian xml_buffer, merge2_physical_id xml_buffer, merge2_radius_arc xml_buffer, merge2_segment_count xml_buffer, merge2_segment_id xml_buffer, merge2_segment_type xml_buffer, merge2_sequence_number xml_buffer, merge2_snow_priority xml_buffer, merge2_street_code xml_buffer, merge2_traffic_direction xml_buffer, merge2_traffic_direction_source xml_buffer, merge3_citygml_class xml_buffer, merge3_citygml_function xml_buffer, merge3_construction_status xml_buffer, merge3_curve_flag xml_buffer, merge3_face_code xml_buffer, merge3_gml_name xml_buffer, merge3_level_end_segment xml_buffer, merge3_level_start_segment xml_buffer, merge3_non_pedestrian xml_buffer, merge3_physical_id xml_buffer, merge3_radius_arc xml_buffer, merge3_segment_count xml_buffer, merge3_segment_id xml_buffer, merge3_segment_type xml_buffer,
      merge3_sequence_number xml_buffer, merge3_snow_priority xml_buffer, merge3_street_code xml_buffer, merge3_traffic_direction xml_buffer, merge3_traffic_direction_source xml_buffer, merge4_citygml_class xml_buffer, merge4_citygml_function xml_buffer, merge4_construction_status xml_buffer, merge4_face_code xml_buffer, merge4_gml_name xml_buffer, merge4_level_end_segment xml_buffer, merge4_level_start_segment xml_buffer, merge4_non_pedestrian xml_buffer, merge4_physical_id xml_buffer, merge4_radius_arc xml_buffer, merge4_segment_count xml_buffer, merge4_segment_id xml_buffer, merge4_segment_type xml_buffer, merge4_sequence_number xml_buffer, merge4_snow_priority xml_buffer, merge4_street_code xml_buffer, merge4_traffic_direction xml_buffer, merge4_traffic_direction_source xml_buffer, node_id_from xml_buffer, node_id_to xml_buffer, non_pedestrian xml_buffer, number_parking_lanes xml_buffer, number_total_lanes xml_buffer, number_travel_lanes xml_buffer, physical_id xml_buffer,
      radius_arc xml_buffer, sanitation_district_boundary_indicator xml_buffer, segment_count xml_buffer, segment_id xml_buffer, segment_type xml_buffer, sequence_number xml_buffer, slope_percent xml_buffer, snow_priority xml_buffer, special_address_place_name xml_buffer, special_address_place_name_2 xml_buffer, special_address_place_name_3 xml_buffer, special_address_place_name_4 xml_buffer, special_address_place_name_5 xml_buffer, special_address_place_name_6 xml_buffer, special_address_place_name_7 xml_buffer, special_address_place_name_8 xml_buffer, special_address_place_name_9 xml_buffer, special_address_type xml_buffer, special_address_type_2 xml_buffer, special_address_type_3 xml_buffer, special_address_type_4 xml_buffer, special_address_type_5 xml_buffer, special_address_type_6 xml_buffer, special_address_type_7 xml_buffer, special_address_type_8 xml_buffer, special_address_type_9 xml_buffer, street_area_2D_sq_m xml_buffer, street_code xml_buffer, street_length_2D_meter xml_buffer, street_length_3D_meter xml_buffer,
      street_pavement_rating_date xml_buffer, street_pavement_rating_num xml_buffer, street_pavement_rating_text xml_buffer, street_segment_width_meter xml_buffer, street_speed_limit_km_h xml_buffer, street_speed_limit_mph xml_buffer, street_width_meter xml_buffer, traffic_direction xml_buffer, traffic_direction_source xml_buffer
Inspector

Bookmark: Filter difficult Centerlines
Note: Test if start level =! end level (~ ramp)
Tester_2
    TEST_CLAUSE = TEST @Value(level_start_segment) != @Value(level_end_segment)
    BOOL_OP = OR
    TEST_DESCRIPTION = ""
    TEST_MODE = Automatic
    PASSED -> Road (writer CITYGML_3)
    PASSED -> Centerlines_filtered
    FAILED -> Tester_3
Note: Test if level =! 0 (~bridge, tunnel)
Tester_3
    TEST_CLAUSE = TEST @Value(level_start_segment) != 0
    BOOL_OP = OR
    TEST_DESCRIPTION = ""
    TEST_MODE = Automatic
    PASSED -> Road (writer CITYGML_3)
    PASSED -> Centerlines_filtered
    FAILED -> Tester_4
Note: Test for specific citygml_function attributes
Tester_4
    TEST_CLAUSE:
      TEST @Value(citygml_function{0}) = 2
      TEST @Value(citygml_function{0}) = 3
      TEST @Value(citygml_function{0}) = 4
      TEST @Value(citygml_function{0}) = 8
      TEST @Value(citygml_function{0}) = 9
    BOOL_OP = OR
    TEST_DESCRIPTION = ""
    TEST_MODE = Automatic
    PASSED -> Road (writer CITYGML_3)
    PASSED -> Centerlines_filtered
    FAILED -> Road (writer CITYGML_2)
    FAILED -> Centerlines_unfiltered
Centerlines_filtered: Inspector
Centerlines_unfiltered: Inspector
